module neutron-ovsdb-impl {

    yang-version 1;
    namespace "urn:opendaylight:params:xml:ns:yang:controller:config:neutron-ovsdb:impl";
    prefix "neutron-ovsdb-impl";

    import config { prefix config; revision-date 2013-04-05; }
    import opendaylight-md-sal-binding { prefix mdsal; revision-date 2013-10-28; }

    description
        "This module contains the base YANG definitions for
        neutron-ovsdb implementation.";

    revision "2015-02-19" {
        description
            "Initial revision.";
    }

    // This is the definition of the service implementation as a module identity.
    identity neutron-ovsdb-impl {
        base config:module-type;

        // Specifies the prefix for generated java classes.
        config:java-name-prefix NeutronOvsdb;
    }

    // Augments the 'configuration' choice node under modules/module.
    augment "/config:modules/config:module/config:configuration" {
        case neutron-ovsdb-impl {
            when "/config:modules/config:module/config:type = 'neutron-ovsdb-impl'";
        }
    }
}
