/*
 * Copyright (c) 2016 Cisco Systems, Inc. and others.  All rights reserved.
 *
 * This program and the accompanying materials are made available under the
 * terms of the Eclipse Public License v1.0 which accompanies this distribution,
 * and is available at http://www.eclipse.org/legal/epl-v10.html
 */

module sxp-mapper-cfg {
    yang-version 1;
    namespace "urn:opendaylight:params:xml:ns:yang:controller:config:groupbasedpolicy:sxp-mapper";
    prefix "sxpm-cfg";

    import config { prefix config; revision-date 2013-04-05; }
    import opendaylight-md-sal-binding { prefix mdsal; revision-date 2013-10-28; }
    import groupbasedpolicy-cfg {prefix gbpcfg; revision-date 2015-11-06; }

    description
        "This module contains the base YANG definitions for
          sxf-mapper impl configuration.";

    revision "2016-03-02" {
        description
            "Initial revision.";
    }

    identity sxp-mapper-impl {
        description
            "sxp-mapper impl module";

        base "config:module-type";
        config:java-name-prefix SxpMapperProvider;
    }

    // Augments the 'configuration' choice node under modules/module.
    augment "/config:modules/config:module/config:configuration" {
        case sxp-mapper-impl {
            when "/config:modules/config:module/config:type = 'sxp-mapper-impl'";
        }
    }
}
