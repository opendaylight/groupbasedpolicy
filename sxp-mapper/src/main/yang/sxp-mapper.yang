/*
 * Copyright (c) 2016 Cisco Systems, Inc. and others.  All rights reserved.
 *
 * This program and the accompanying materials are made available under the
 * terms of the Eclipse Public License v1.0 which accompanies this distribution,
 * and is available at http://www.eclipse.org/legal/epl-v10.html
 */

module sxp-mapper {
    yang-version 1;
    namespace "urn:opendaylight:params:xml:ns:yang:controller:config:groupbasedpolicy:sxp-mapper:service";
    prefix "sxpm";

    import sxp-database { prefix sxp-database; revision-date 2016-03-08; }
    import ietf-inet-types { prefix inet; revision-date 2013-07-15; }

    description
        "This module contains the YANG definitions for
          sxf-mapper implementation.";

    revision "2016-03-07" {
        description
            "Initial revision.";
    }


    rpc send-ip-sgt-binding {
        description "Provides sending IP/SGT binding to peers";
        input {
            list ip-sgt-binding {
                min-elements 1;
                key "ip-prefix sgt";
                leaf ip-prefix {
                    type inet:ip-prefix;
                }
                leaf sgt {
                    type sxp-database:sgt;
                }
            }
            leaf-list peers {
                description "If empty then binding will be broadcasted.";
                type inet:ip-address;
            }
        }
        output {
            leaf error {
                type string;
            }
        }
    }

    rpc remove-ip-sgt-binding {
        description "Removes given IP/SGT bindings on peers.";
        input {
            leaf-list ip-prefix {
                type inet:ip-prefix;
            }
            leaf-list peers {
                description "If empty then the binding will be removed from Master DB.";
                type inet:ip-address;
            }
        }
        output {
            leaf error {
                type string;
            }
        }
    }
}
