/*
 * Copyright (c) 2016 Cisco Systems, Inc. and others. All rights reserved.
 *
 * This program and the accompanying materials are made available under the
 * terms of the Eclipse Public License v1.0 which accompanies this distribution,
 * and is available at http://www.eclipse.org/legal/epl-v10.html
 */

module neutron-vpp-mapper-impl {

    yang-version 1;
    namespace "urn:opendaylight:params:xml:ns:yang:controller:config:neutron-vpp-mapper:impl";
    prefix "neutron-vpp-mapper-impl";

    import config { prefix config; revision-date 2013-04-05; }
    import opendaylight-md-sal-binding { prefix mdsal; revision-date 2013-10-28; }

    description
        "This module contains the base YANG definitions for
        neutron-vpp-mapper implementation.";

    revision "2016-04-25" {
        description
            "Initial revision.";
    }

    // This is the definition of the service implementation as a module identity.
    identity neutron-vpp-mapper-impl {
        base config:module-type;

        // Specifies the prefix for generated java classes.
        config:java-name-prefix NeutronVppMapper;
    }

    // Augments the 'configuration' choice node under modules/module.
    augment "/config:modules/config:module/config:configuration" {
        case neutron-vpp-mapper-impl {
            when "/config:modules/config:module/config:type = 'neutron-vpp-mapper-impl'";
        }
    }
}
