/*
 * Copyright (c) 2014 Cisco Systems, Inc. and others.  All rights reserved.
 *
 * This program and the accompanying materials are made available under the
 * terms of the Eclipse Public License v1.0 which accompanies this distribution,
 * and is available at http://www.eclipse.org/legal/epl-v10.html
 */

module ne-location-provider-cfg {
    yang-version 1;
    namespace "urn:opendaylight:params:xml:ns:yang:controller:config:ne:location:provider:cfg";
    prefix "ne-location-provider-cfg";

    import config { prefix config; revision-date 2013-04-05; }
    import opendaylight-md-sal-binding { prefix mdsal; revision-date 2013-10-28; }

    description
        "This module contains the base YANG definitions for
          ne location provider implementation.";

    revision "2016-04-21" {
        description
            "Initial revision.";
    }

    identity ne-location-provider {
        base "config:module-type";

        config:java-name-prefix NeLocationProvider;
    }

    // Augments the 'configuration' choice node under modules/module.
    augment "/config:modules/config:module/config:configuration" {
        case ne-location-provider {
            when "/config:modules/config:module/config:type = 'ne-location-provider'";
        }
    }
}
