module ui-backend-impl {

    yang-version 1;
    namespace "urn:opendaylight:params:xml:ns:yang:controller:config:ui-backend:impl";
    prefix "ui-backend-impl";

    import config { prefix config; revision-date 2013-04-05; }
    import opendaylight-md-sal-binding { prefix mdsal; revision-date 2013-10-28; }

    description
        "This module contains the base YANG definitions for
        ui-backend implementation.";

    revision "2015-05-11" {
        description
            "Initial revision.";
    }

    // This is the definition of the service implementation as a module identity.
    identity ui-backend-impl {
        base config:module-type;

        // Specifies the prefix for generated java classes.
        config:java-name-prefix UiBackend;
    }

    // Augments the 'configuration' choice node under modules/module.
    augment "/config:modules/config:module/config:configuration" {
        case ui-backend-impl {
            when "/config:modules/config:module/config:type = 'ui-backend-impl'";

            container data-broker {
                uses config:service-ref {
                    refine type {
                        mandatory true;
                        config:required-identity mdsal:binding-async-data-broker;
                    }
                }
            }

            container rpc-registry {
                uses config:service-ref {
                    refine type {
                        mandatory true;
                        config:required-identity mdsal:binding-rpc-registry;
                    }
                }
            }

        }
    }
}
