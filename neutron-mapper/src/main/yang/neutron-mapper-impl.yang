module neutron-mapper-impl {

    yang-version 1;
    namespace "urn:opendaylight:params:xml:ns:yang:controller:config:neutron-mapper:impl";
    prefix "neutron-mapper-impl";

    import config { prefix config; revision-date 2013-04-05; }
    import opendaylight-md-sal-binding { prefix mdsal; revision-date 2013-10-28; }

    description
        "This module contains the base YANG definitions for
        neutron-mapper implementation.";

    revision "2015-02-19" {
        description
            "Initial revision.";
    }

    // This is the definition of the service implementation as a module identity.
    identity neutron-mapper-impl {
        base config:module-type;

        // Specifies the prefix for generated java classes.
        config:java-name-prefix NeutronMapper;
    }

    // Augments the 'configuration' choice node under modules/module.
    augment "/config:modules/config:module/config:configuration" {
        case neutron-mapper-impl {
            when "/config:modules/config:module/config:type = 'neutron-mapper-impl'";
        }
    }
}
