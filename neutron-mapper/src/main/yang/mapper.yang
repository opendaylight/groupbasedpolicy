module neutron-mapper {
    yang-version 1;

    namespace "urn:opendaylight:groupbasedpolicy:neutron-mapper";
    prefix "gbp-neutron-mapper";

    import gbp-common {prefix gbp-common;}
    import endpoint {prefix gbp-endpoint;}
    import ietf-inet-types {
        prefix inet;
        revision-date 2010-09-24;
    }

    description 
        "This module defines the mapping model between Neutron IDs and GBP IDs. 
        These mappings are used just internaly and are NOT EXPORTED.";

    revision "2015-02-23" {
        description
            "Initial revision.";
    }

    grouping tenant-id-fields {
        leaf tenant-id {
                description "A unique ID for the tenant";
                mandatory true;
                type gbp-common:tenant-id;
        }
    }

    container mappings {
        config false;
        container network-mappings {
            list network-mapping {
                key network-id;
                leaf network-id {
                    description "A unique ID for the neutron network == gbp l2-flood-domain";
                    type gbp-common:unique-id;
                }
                leaf l2-bridge-domain-id {
                    description "A unique ID of l2-bridge-domain generated for neutron network";
                    type gbp-common:l2-bridge-domain-id;
                }
                leaf l3-context-id {
                    description "A unique ID of l3-context generated for neutron network";
                    type gbp-common:l3-context-id;
                }
            }
        }
    }

}
