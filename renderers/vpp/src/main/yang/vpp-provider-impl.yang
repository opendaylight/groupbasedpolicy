/*
 * Copyright (c) 2014 Cisco Systems, Inc. and others.  All rights reserved.
 *
 * This program and the accompanying materials are made available under the
 * terms of the Eclipse Public License v1.0 which accompanies this distribution,
 * and is available at http://www.eclipse.org/legal/epl-v10.html
 */

module vpp-provider-impl {
    yang-version 1;
    namespace "urn:opendaylight:params:xml:ns:yang:controller:config:vpp-provider:impl";
    prefix "vpp-provider-impl";

    import config { prefix config; revision-date 2013-04-05; }
    import opendaylight-md-sal-binding { prefix mdsal; revision-date 2013-10-28; }
    import ietf-yang-types { prefix "yang"; revision-date 2013-07-15; }
    import opendaylight-sal-binding-broker-impl { prefix sal-broker; revision-date 2013-10-28;}
    import groupbasedpolicy-cfg { prefix gbpcfg; revision-date 2015-11-06; }

    description
        "This module contains the base YANG definitions for
          vpp-provider impl implementation.";

    revision "2016-04-25" {
        description
            "Initial revision.";
    }

    identity vpp-provider-impl {
        base "config:module-type";

        config:java-name-prefix GbpVppProvider;
    }

    // Augments the 'configuration' choice node under modules/module.
    augment "/config:modules/config:module/config:configuration" {
        case vpp-provider-impl {
            when "/config:modules/config:module/config:type = 'vpp-provider-impl'";
        }
    }
}
