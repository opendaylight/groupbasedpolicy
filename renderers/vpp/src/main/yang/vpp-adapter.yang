/*
 * Copyright (c) 2016 Cisco Systems, Inc. and others.  All rights reserved.
 *
 * This program and the accompanying materials are made available under the
 * terms of the Eclipse Public License v1.0 which accompanies this distribution,
 * and is available at http://www.eclipse.org/legal/epl-v10.html
 */

module vpp-adapter {
    yang-version 1;

    namespace "urn:opendaylight:groupbasedpolicy:vpp_adapter";
    prefix "vpp-adapter";

    import vpp-renderer { prefix "vpp-renderer"; }
    import network-topology { prefix nt; revision-date 2013-10-21; }
    import opendaylight-l2-types { prefix l2-types; revision-date "2013-08-27"; }
    import ietf-yang-types { prefix yang-types; revision-date "2013-07-15"; }
    import ietf-inet-types { prefix "inet-types"; }

    description
        "This module allows external plugins to use VPP renderer by calling defined RPCs.";

    revision "2016-12-01" {
        description
            "Initial revision.";
    }

    typedef vxlan-vni-type {
        type uint32 {
            range "1 .. 16777214";
        }
    }

    grouping bridge-domain-attributes {
        uses vpp-renderer:bridge-domain-base-attributes;
        leaf unknown-unicast-flood {
            type boolean;
            default "True";
        }
        choice tunnel-type {
            case vxlan {
                leaf vni {
                    type vxlan-vni-type;
                }
            }
            case vlan {
                leaf vlan-id {
                    type l2-types:vlan-id;
                }
            }
        }
    }

    grouping bridge-domain-nodes {
        uses bridge-domain-id;
            leaf-list bridge-domain-node {
                min-elements 1;
                type nt:node-id;
            }
    }

    grouping bridge-domain-id {
        leaf bridge-domain-id {
            mandatory true;
            type string;
        }
    }

    rpc create-virtual-bridge-domain-on-nodes {
        description "Creates a virtual bridge domain on specific nodes.
                     If no node is specified, the bridge domain will be
                     defined in datastore and can be cloned on nodes
                     later. Physical interfaces on node can be also
                     specified in cases when bridge domains exceed the
                     virtual domain (aka provider networks).";
        input {
            uses bridge-domain-attributes;
        }
    }

    rpc clone-virtual-bridge-domain-on-nodes {
        description "If a virtual bridge domain is already defined in DS,
                     it can be cloned to other nodes by using this RPC.
                     Parameters that are already known don't have to be
                     specified again. They are found based on provided
                     bridge domain ID.";
        input {
            uses bridge-domain-nodes;
        }
    }

    rpc delete-virtual-bridge-domain-from-nodes {
        description "Removes a virtual bridge domain from nodes. If no node
                     is specified, the definition of the bridge domain will
                     be removed from the DS.";
        input {
            uses bridge-domain-nodes;
        }
    }

    rpc create-interface-on-node {
        description "Creates an interface on a node based on provided input.";
        input {
            uses vpp-renderer:interface-attributes;
        }
    }

    rpc delete-interface-from-node {
        description "Removes an interface from a node.";
        input {
            uses vpp-renderer:interface-location;
        }
    }

    rpc add-interface-to-bridge-domain {
        description "Adds existing interface on a node to a specified bridge
                     domain.";
        input {
            uses vpp-renderer:interface-location;
            uses bridge-domain-id;
        }
    }

    rpc del-interface-from-bridge-domain {
        description "Removes existing interface on a node from a specified bridge
                     domain.";
        input {
            uses vpp-renderer:interface-location;
        }
    }
}
