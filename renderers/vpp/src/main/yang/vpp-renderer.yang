/*
 * Copyright (c) 2016 Cisco Systems, Inc. and others.  All rights reserved.
 *
 * This program and the accompanying materials are made available under the
 * terms of the Eclipse Public License v1.0 which accompanies this distribution,
 * and is available at http://www.eclipse.org/legal/epl-v10.html
 */

module vpp-renderer {
    yang-version 1;

    namespace "urn:opendaylight:groupbasedpolicy:vpp_renderer";
    prefix "vpp-renderer";

    import base-endpoint { prefix base-ep; revision-date 2016-04-27; }
    import network-topology { prefix nt; revision-date 2013-10-21; }
    import opendaylight-l2-types { prefix l2-types; revision-date "2013-08-27"; }
    import ietf-yang-types { prefix yang-types; revision-date "2013-07-15"; }
    import ietf-inet-types { prefix "inet-types"; }
    import yang-ext {prefix ext; revision-date "2013-07-09";}
    import v3po { prefix v3po; }
    import ietf-interfaces { prefix if; }
    import renderer { prefix rend; }

    description
        "This module is a baseline for the group-based policy vpp renderer model.";

    revision "2016-04-25" {
        description
            "Initial revision.";
    }

    identity network-type-base {
        description "Base for Network Types.";
    }

    identity flat-network {
        description "Flat Provider Network Type";
        base network-type-base;
    }

    identity vlan-network {
        description "VLAN Provider Network Type";
        base network-type-base;
    }

    typedef network-type {
        description "Type of Network.";
        type identityref {
            base network-type-base;
        }
    }

    grouping bridge-domain-base-attributes {
        leaf id {
            description "Same as in VBD.";
            type string;
        }
        leaf description {
           type string;
        }
        list physical-location-ref {
            description
                "Refers to physical interfaces on vpp nodes through which external
                 nodes belonging to the same bridge-domain can be reached.";
            key "node-id";
            leaf node-id {
                description "Refers to a VPP node.";
                type nt:node-id;
            }
            leaf-list interface {
                description "Physical interface on the VPP node.";
                type string;
            }
        }
    }

    grouping interface-attributes {
        uses interface-location;
        leaf description {
            description "Additional description of the vpp-endpoint";
            type string;
        }
        choice interface-type-choice {
            mandatory true;
            case vhost-user-case {
                leaf socket {
                    description "Identifier of a vhost user";
                    type string {
                        length 1..255;
                    }
                }
            }
            case tap-case {
                leaf name {
                    description "Identifier of a tap port";
                    mandatory true;
                    type string {
                        length 1..255;
                    }
                }
                leaf physical-address {
                    description "MAC address of a tap port";
                    type yang-types:phys-address;
                }

                leaf dhcp-server-address {
                    description "IP address of a dhcp port";
                    type inet-types:ip-address;
                }
            }
            case loopback-case {
                leaf phys-address {
                    description "MAC address of a loopback interface";
                    type yang-types:phys-address;
                }
                leaf ip-address {
                    description "Ip address of a loopback interface";
                    type inet-types:ip-address;
                }
                leaf ip-prefix {
                    description "Ip address prefix of a loopback interface";
                    type inet-types:ip-prefix;
                }
                leaf bvi {
                    description "Enable/disable BVI for loopback interface";
                    type boolean;
                }
            }
        }
    }

    grouping interface-location {
        leaf vpp-node-id {
            description "Id of a VPP node represented as a mount-point in netconf topology.";
            mandatory true;
            type nt:node-id;
        }
        leaf vpp-interface-name {
            description "Name of interface for the endpoint on VPP";
            mandatory true;
            type string;
        }
    }

    grouping gbp-subnet-base-attributes {
        leaf id {
            description "Subnet UUID of neutron subnet call.";
            type string;
        }
        leaf cidr {
            type inet:ip-prefix;
            description "cidr representing IP range for this subnet, based on IP version";
        }
        leaf gateway-ip {
            type inet:ip-address;
            description "default gateway used by devices in this subnet";
        }
        list allocation-pools {
            description "Sub-ranges of cidr available for dynamic allocation to ports";
            key start;
            leaf start {
                type inet:ip-address;
            }
            leaf end {
                type inet:ip-address;
            }
        }
    }

    container config {
        list vpp-endpoint {
            description "Renderer creates/removes interface on VPP node based on given parameters.";

            key "context-type context-id address-type address";
            uses base-ep:address-endpoint-key;

            uses interface-attributes;
        }

        list gbp-bridge-domain {
            key "id";
            uses bridge-domain-base-attributes;
            leaf type {
                mandatory true;
                type network-type;
            }
            leaf vlan {
                when "type = 'vlan-network'";
                type l2-types:vlan-id;
            }
        }

        list gbp-subnet {
            key "id";
            uses gbp-subnet-base-attributes;
        }
    }

    augment "rend:renderers/rend:renderer/rend:renderer-nodes/rend:renderer-node" {
        description "Augmentation for recognized VPP interfaces";
        ext:augment-identifier "vpp-interface-augmentation";
        list physical-interface {
            key interface-name;
            leaf interface-name {
                type string;
            }
            leaf type {
                type identityref {
                    base if:interface-type;
                }
            }
            leaf-list address {
                type inet-types:ip-address;
            }
            leaf external {
                type boolean;
                default  "false";
            }
        }
    }

    augment "/vpp-renderer:config/vpp-renderer:vpp-endpoint" {
        ext:augment-identifier "exclude-from-policy";
        leaf exclude-from-policy {
            description "Device attached as an endpoint may act as network element,
                         e.g. qrouter attached via tap interface.";
            type empty;
        }
    }
}
