/*
 * Copyright (c) 2014 Cisco Systems, Inc. and others.  All rights reserved.
 *
 * This program and the accompanying materials are made available under the
 * terms of the Eclipse Public License v1.0 which accompanies this distribution,
 * and is available at http://www.eclipse.org/legal/epl-v10.html
 */

module ovssfc {
    yang-version 1;

    namespace "urn:opendaylight:groupbasedpolicy:ovssfc";
    prefix "ovssfc";

    description
        "This module defines the group-based policy ovssfc renderer model.";

    revision "2015-10-30" {
        description
                "Initial revision.";
    }

    container ovssfc-renderer {
        leaf ovssfc-renderer-name {
            type string;
        }
    }
}
