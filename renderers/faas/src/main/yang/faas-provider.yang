/*
 * Copyright (c) 2015 Huawei Technologies and others.  All rights reserved.
 *
 * This program and the accompanying materials are made available under the
 * terms of the Eclipse Public License v1.0 which accompanies this distribution,
 * and is available at http://www.eclipse.org/legal/epl-v10.html
 */

module faas-provider {
    yang-version 1;
    namespace "urn:opendaylight:params:xml:ns:yang:controller:config:faas-provider";
    prefix "faas-provider";

    import config { prefix config; revision-date 2013-04-05; }

    description
        "This module contains the base YANG definitions for faas-provider
        services.";

    revision "2015-10-09" {
        description
                "Initial revision.";
    }

    identity faas-provider {
        base "config:service-type";
        config:java-class "org.opendaylight.yang.gen.v1.urn.opendaylight.groupbasedpolicy.faas.rev151009.FaasData";
    }
}
