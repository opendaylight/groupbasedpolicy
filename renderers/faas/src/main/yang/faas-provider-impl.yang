/*
 * Copyright (c) 2015 Huawei Technologies and others.  All rights reserved.
 *
 * This program and the accompanying materials are made available under the
 * terms of the Eclipse Public License v1.0 which accompanies this distribution,
 * and is available at http://www.eclipse.org/legal/epl-v10.html
 */

module faas-provider-impl {
    yang-version 1;
    namespace "urn:opendaylight:params:xml:ns:yang:controller:config:faas-provider:impl";
    prefix "faas-provider-impl";

    import config { prefix config; revision-date 2013-04-05; }
    import opendaylight-md-sal-binding { prefix mdsal; revision-date 2013-10-28; }
    import opendaylight-sal-binding-broker-impl { prefix sal-broker; revision-date 2013-10-28; }
    import groupbasedpolicy-cfg { prefix gbpcfg; revision-date 2015-11-06; }

    description
        "This module contains the base YANG definitions for faas-provider
        impl implementation.";

    revision "2015-10-09" {
        description
                "Initial revision.";
    }

    identity faas-provider-impl {
        base "config:module-type";

        config:java-name-prefix FaasProvider;
    }

    // Augments the 'configuration' choice node under modules/module.
    augment "/config:modules/config:module/config:configuration" {
        case faas-provider-impl {
            when "/config:modules/config:module/config:type = 'faas-provider-impl'";
        }
    }
}
