/*
 * Copyright (c) 2015 Huawei Technologies and others.  All rights reserved.
 *
 * This program and the accompanying materials are made available under the
 * terms of the Eclipse Public License v1.0 which accompanies this distribution,
 * and is available at http://www.eclipse.org/legal/epl-v10.html
 */

module faas-endpoint {
    yang-version 1;
    namespace "urn:opendaylight:faas:faas-endpoint";
    prefix "faas-endpoint";

    import yang-ext { prefix ext; revision-date "2013-07-09"; }
    import endpoint { prefix endpoint; revision-date 2014-04-21; }
    import faas-common { prefix faas-common; revision-date 2015-10-13; }

    revision 2015-10-09 {
        description "Initial revision";
    }

    grouping faas-port-ref {
        leaf faas-port-ref-id {
            description "faas port cross reference";
            type faas-common:uuid;
        }
    }
    augment "/endpoint:endpoints/endpoint:endpoint" {
        ext:augment-identifier "faas-endpoint-context";
        uses faas-port-ref;
    }

    augment "/endpoint:register-endpoint/endpoint:input" {
        ext:augment-identifier "faas-endpoint-context-input";
        uses faas-port-ref;
    }
}
