/*
 * Copyright (c) 2014 Cisco Systems, Inc. and others.  All rights reserved.
 *
 * This program and the accompanying materials are made available under the
 * terms of the Eclipse Public License v1.0 which accompanies this distribution,
 * and is available at http://www.eclipse.org/legal/epl-v10.html
 */

module faas {
    yang-version 1;

    namespace "urn:opendaylight:groupbasedpolicy:faas";
    prefix "faas";

    import gbp-common { prefix gbp-common; revision-date 2014-04-21; }
    import faas-common { prefix faas-common; revision-date 2015-10-13; }
    import endpoint { prefix endpoint; revision-date 2014-04-21; }
    import resolved-policy { prefix resolved-policy; revision-date 2015-08-28; }

    description
        "This module defines the group-based policy faas renderer model.";

    revision "2015-10-09" {
        description
                "Initial revision.";
    }

    typedef scope-type {
        type enumeration {
            enum private {
                description "private scope within a tenant domain";
            }
            enum public {
                description "public scope that is exposed outside the tenant domain such as the Internet";
            }
        }
    }
    typedef service-communication-layer {
        type enumeration {
            enum layer-undefined {
                description "Undefined layer";
            }
            enum layer-2 {
                description "layer 2";
            }
            enum layer-3 {
                description "layer 3";
            }
        }
    }
    grouping has-contract-key {
        leaf contract-tenant-id {
            description "Related tenant id";
            type gbp-common:tenant-id;
        }

        leaf contract-id {
            description "Related contract id";
            type gbp-common:contract-id;
        }
    }

    grouping has-logical-entity {
        leaf logical-router-id {
            type faas-common:uuid;
        }
        leaf logical-switch-id {
            type faas-common:uuid;
        }
        leaf-list gbp-subnet-id {
            type gbp-common:subnet-id;
        }
    }

    container logical-networks {
        description "The mapped logical networks based on GBP resolved services";

        config false;

        list logical-network {
            description "Mapped logical network for an EPG-Contract-EPG service";

            key "consumer-epg-id contract-id provider-epg-id consumer-tenant-id provider-tenant-id";

            uses resolved-policy:has-consumer-epg-key;
            uses has-contract-key;
            uses resolved-policy:has-provider-epg-key;
            leaf communication-layer {
                description "logical network communication layer";
                type service-communication-layer;
            }
            container consumer-network {
                uses has-logical-entity;
                leaf network-scope-type {
                    description "if public, it means the router has a public access port";
                    default private;
                    type scope-type;
                }
            }
            container provider-network {
                uses has-logical-entity;
                leaf network-scope-type {
                    description "if public, it means the router has a public access port";
                    default private;
                    type scope-type;
                }
            }
        }
    }

    grouping tenant-pair-id {
        leaf gbp-tenant-id {
            type gbp-common:tenant-id;
        }
        leaf faas-tenant-id {
            type faas-common:uuid;
        }
    }
    container mapped-tenants-entities {

        config false;

        list mapped-tenant {
            key "gbp-tenant-id";
            uses tenant-pair-id;
        }
        list mapped-entity {
            key "gbp-tenant-id";
            leaf gbp-tenant-id {
                type gbp-common:tenant-id;
            }
            list mapped-contract {
                key "gbp-contract-id";
                leaf gbp-contract-id {
                    type gbp-common:contract-id;
                }
                leaf faas-security-rules-id {
                    type faas-common:uuid;
                }
            }
            list mapped-subnet {
                key "gbp-subnet-id";
                leaf gbp-subnet-id {
                    type gbp-common:subnet-id;
                }
                leaf faas-subnet-id {
                    type faas-common:uuid;
                }
            }
            list mapped-endpoint {
                key "l2-context mac-address";
                uses endpoint:l2-key;
                leaf endpoint-location {
                    type faas-common:uuid;
                }
            }
        }
    }
}
