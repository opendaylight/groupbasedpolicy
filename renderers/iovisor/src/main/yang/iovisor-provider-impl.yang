/*
 * Copyright (c) 2015 Cisco System.  All rights reserved.
 *
 * This program and the accompanying materials are made available under the
 * terms of the Eclipse Public License v1.0 which accompanies this distribution,
 * and is available at http://www.eclipse.org/legal/epl-v10.html
 */

module iovisor-provider-impl {
    yang-version 1;
    namespace "urn:opendaylight:params:xml:ns:yang:controller:config:iovisor-provider:impl";
    prefix "iovisor-provider-impl";

    import config { prefix config; revision-date 2013-04-05; }
    import opendaylight-md-sal-binding { prefix mdsal; revision-date 2013-10-28; }
    import opendaylight-sal-binding-broker-impl { prefix sal-broker; revision-date 2013-10-28; }
    import groupbasedpolicy-cfg { prefix gbpcfg; revision-date 2015-11-06; }

    description
        "This module contains the base YANG definitions for iovisor-provider
        impl implementation.";

    revision "2015-10-30" {
        description
                "Initial revision.";
    }

    identity iovisor-provider-impl {
        base "config:module-type";

        config:java-name-prefix IovisorProvider;
    }

    // Augments the 'configuration' choice node under modules/module.
    augment "/config:modules/config:module/config:configuration" {
        case iovisor-provider-impl {
            when "/config:modules/config:module/config:type = 'iovisor-provider-impl'";
        }
    }
}
