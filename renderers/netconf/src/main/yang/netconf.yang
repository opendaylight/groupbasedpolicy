/*
 * Copyright (c) 2014 Cisco Systems, Inc. and others.  All rights reserved.
 *
 * This program and the accompanying materials are made available under the
 * terms of the Eclipse Public License v1.0 which accompanies this distribution,
 * and is available at http://www.eclipse.org/legal/epl-v10.html
 */

module netconf {
    yang-version 1;

    namespace "urn:opendaylight:groupbasedpolicy:netconf";
    prefix "netconf";

    description
        "This module defines the group-based policy netconf renderer model.";

    revision "2015-10-30" {
        description
                "Initial revision.";
    }

    container netconf-renderer {
        leaf netconf-renderer-name {
            type string;
        }
    }
}
