module ned {

    prefix ios;
    namespace
        "urn:ios";

    import tailf-common {
        prefix tailf;
    }

    import ietf-inet-types {
        prefix inet;
        revision-date 2013-07-15;
    }

    import ietf-yang-types {
        prefix yang;
      }

    description
        "This file was adapted to be parsed by yangtools for groupbasedpolicy project purpose";

    revision
        2016-03-08;

/// ========================================================================
/// typedefs
/// ========================================================================

    typedef class-name-type {
        type union {
            type string {
                // Note: leafref can't be used here due to part of union.
                //path "/ios:native/class-map/name";
                tailf:info "WORD;;class-map name";
            }
            type enumeration {
                enum class-default {
                    tailf:info "System default class matching otherwise "+
                    "unclassified packet";
                }
            }
        }
    }

    typedef cos_value-type {
        type union {
            type uint8 {
                tailf:info "<0-7>;;new cos value";
                range "0..7";
            }
            type enumeration {
                enum cos {
                    tailf:info "Set packet cos from cos";
                }
                enum dscp {
                    tailf:info "Set packet cos from dscp";
                }
                enum exp {
                    tailf:info "Set packet cos from exp";
                }
                enum precedence {
                    tailf:info "Set packet cos from precedence";
                }
            }
        }
    }

    typedef dscp-type {
        type union {
            type uint8 {
                tailf:info "<0-63>;;Differentiated services codepoint value";
                range "0..63";
            }
            type enumeration {
                enum af11 {
                    tailf:info "Match packets with AF11 dscp (001010)";
                    value 10;
                }
                enum af12 {
                    tailf:info "Match packets with AF12 dscp (001100)";
                    value 12;
                }
                enum af13 {
                    tailf:info "Match packets with AF13 dscp (001110)";
                    value 14;
                }
                enum af21 {
                    tailf:info "Match packets with AF21 dscp (010010)";
                    value 18;
                }
                enum af22 {
                    tailf:info "Match packets with AF22 dscp (010100)";
                    value 20;
                }
                enum af23 {
                    tailf:info "Match packets with AF23 dscp (010110)";
                    value 22;
                }
                enum af31 {
                    tailf:info "Match packets with AF31 dscp (011010)";
                    value 26;
                }
                enum af32 {
                    tailf:info "Match packets with AF32 dscp (011100)";
                    value 28;
                }
                enum af33 {
                    tailf:info "Match packets with AF33 dscp (011110)";
                    value 30;
                }
                enum af41 {
                    tailf:info "Match packets with AF41 dscp (100010)";
                    value 34;
                }
                enum af42 {
                    tailf:info "Match packets with AF42 dscp (100100)";
                    value 36;
                }
                enum af43 {
                    tailf:info "Match packets with AF43 dscp (100110)";
                    value 38;
                }
                enum cs1 {
                    tailf:info "Match packets with CS1(precedence 1) dscp" +
                    " (001000)";
                    value 8;
                }
                enum cs2 {
                    tailf:info "Match packets with CS2(precedence 2) dscp" +
                    " (010000)";
                    value 16;
                }
                enum cs3 {
                    tailf:info "Match packets with CS3(precedence 3) dscp" +
                    " (011000)";
                    value 24;
                }
                enum cs4 {
                    tailf:info "Match packets with CS4(precedence 4) dscp" +
                    " (100000)";
                    value 32;
                }
                enum cs5 {
                    tailf:info "Match packets with CS5(precedence 5) dscp" +
                    " (101000)";
                    value 40;
                }
                enum cs6 {
                    tailf:info "Match packets with CS6(precedence 6) dscp" +
                    " (110000)";
                    value 48;
                }
                enum cs7 {
                    tailf:info "Match packets with CS7(precedence 7) dscp" +
                    " (111000)";
                    value 56;
                }
                enum "default" {
                    tailf:code-name "dscp_default";
                    tailf:info "Match packets with default dscp (000000)";
                    value 0;
                }
                enum dscp {
                    tailf:info "Set packet dscp from dscp";
                }
                enum ef {
                    tailf:info "Match packets with EF dscp (101110)";
                    value 46;
                }
                enum precedence {
                    tailf:info "Set packet dscp from precedence";
                }
            }
        }
    }

    typedef exp_value-type {
        type union {
            type uint8 {
                tailf:info "<0-7>;;new exp";
                range "0..7";
            }
            type enumeration {
                enum cos {
                    tailf:info "Set packet exp from cos";
                }
                enum dscp {
                    tailf:info "Set packet exp from dscp";
                }
                enum exp {
                    tailf:info "Set packet exp from exp";
                }
                enum precedence {
                    tailf:info "Set packet exp from precedence";
                }
            }
        }
    }

    typedef percentage-type {
        type uint8 {
            tailf:info "<1-100>;;Percentage";
            range "1..100";
        }
    }

    typedef police-bps-type {
        type uint64 {
            tailf:info "<8000-64000000000>;;Bits per second";
            range "8000..64000000000";
        }
    }

    typedef police-burst-type {
        type uint32 {
            tailf:info "<1000-512000000>;;Burst bytes";
            range "1000..512000000";
        }
    }

    typedef police-packets-bytes-type {
        type enumeration {
            enum packets {
                tailf:info "Treat 'burst' value as packets";
            }
            enum bytes {
                tailf:info "Treat 'burst' value as bytes";
            }
        }
    }

    typedef police-pps-bps-type {
        type enumeration {
            enum pps {
                tailf:info "pps  Treat 'rate' value in "+
                "packets-per-second";
            }
            enum bps {
                tailf:info "pps  Treat 'rate' value in "+
                "bytes-per-second";
            }
        }
    }

    typedef policy-action-type {
        type enumeration {
            enum bandwidth  {
                tailf:code-name policy_bandwidth;
                tailf:info "Bandwidth";
            }
            enum compression  {
                tailf:info "Activate Compression";
            }
            enum dbl {
                tailf:info "Dynamic buffer limiting";
            }
            enum drop  {
                tailf:info "Drop all packets";
            }
            enum estimate {
                tailf:info "Estimate resources required for this class";
            }
            enum fair-queue  {
                tailf:info "Enable Flow-based Fair Queuing in this Class";
            }
            enum forward {
                tailf:info "Forward service-path action";
            }
            enum netflow-sampler {
                tailf:info "NetFlow action";
            }
            enum police  {
                tailf:info "Police";
            }
            enum priority {
                tailf:code-name policy_priority;
                tailf:info "Strict Scheduling Priority for this Class";
            }
            enum queue-limit  {
                tailf:info "Queue Max Threshold for Tail Drop";
            }
            enum random-detect {
                tailf:info "Enable Random Early Detection as drop policy";
            }
            enum service-policy {
                tailf:info "Configure Flow Next";
            }
            enum set {
                tailf:info "Set QoS values";
            }
            enum shape {
                tailf:code-name policy_shape;
                tailf:info "Traffic Shaping";
            }
            enum trust {
                tailf:info "Set trust value for the class";
            }
            enum queue-buffers {
               tailf:info "queue buffer";
            }
        }
    }

    typedef prec_value-type {
        type union {
            type uint8 {
                tailf:info "<0-7>;;new precedence";
                range "0..7";
            }
            type enumeration {
                enum cos {
                    tailf:info "Set packet precedence from cos";
                }
                enum dscp {
                    tailf:info "Set packet precedence from dscp";
                }
                enum exp {
                    tailf:info "Set packet precedence from exp";
                }
                enum precedence {
                    tailf:info "Set packet precedence from precedence";
                }
            }
        }
    }

    typedef precedence-type {
        type union {
            type uint8 {
                tailf:info "<0-7>;;Precedence value";
                range "0..7";
            }
            type enumeration {
                enum critical {
                    tailf:info "Set packets with critical precedence (5)";
                }
                enum flash {
                    tailf:info "Set packets with flash precedence (3)";
                }
                enum flash-override {
                    tailf:info "Set packets with flash override precedence (4)";
                }
                enum immediate {
                    tailf:info "Set packets with immediate precedence (2)";
                }
                enum internet {
                    tailf:code-name "prec_internet";
                    tailf:info "Set packets with internetwork control"+
                    " precedence (6)";
                }
                enum network {
                    tailf:info "Set packets with network control precedence"+
                    " (7)";
                }
                enum priority {
                    tailf:code-name "prec_priority";
                    tailf:info "Set packets with priority precedence (1)";
                }
                enum routine {
                    tailf:info "Set packets with routine precedence (0)";
                }
            }
        }
    }

    typedef precedence-type2 {
        type union {
            type uint8 {
                tailf:info "<0-7>;;IP precedence";
                range "0..7";
            }
            type enumeration {
                enum rsvp {
                    tailf:code-name "prec_rsvp";
                    tailf:info "rsvp traffic";
                }
            }
        }
    }

    typedef qos_value-type {
        type union {
            type uint8 {
                tailf:info "<0-99>;;new qos-group";
                range "0..99";
            }
            type enumeration {
                enum cos {
                    tailf:info "Set packet qos from cos";
                }
                enum dscp {
                    tailf:info "Set packet qos from dscp";
                }
                enum exp {
                    tailf:info "Set packet qos from exp";
                }
                enum precedence {
                    tailf:info "Set packet qos from precedence";
                }
            }
        }
    }

/// ========================================================================
/// groupings
/// ========================================================================

    grouping class-map-appnav-not-match-grouping {
        // class-map * / peer
        leaf peer {
        when "../../../type = 'appnav'";
        tailf:info "APPNAV Peer Filter";
        description "APPNAV Peer Filter";
        type string {
            tailf:info "H.H.H;;Device ID";
            }
        }
    }

    grouping class-map-appnav-match-grouping {
        // class-map * / peer
        leaf peer {
            when "../../type = 'appnav'";
            tailf:info "APPNAV Peer Filter";
            description "APPNAV Peer Filter";
            type string {
                tailf:info "H.H.H;;Device ID";
            }
        }
    }

    grouping class-map-match-grouping {
        // class-map * / match application
        container application {
            tailf:info "Application to match";
            description "Application to match";
            container application-group {
                tailf:info "Application Group to match";
                description "Application Group to match";
                leaf telepresence-group {
                    tailf:info "Telepresence Group";
                    description "Telepresence Group";
                    tailf:cli-full-command;
                    type empty;
                }
                leaf vmware-group {
                    tailf:info "VMWARE Group";
                    description "VMWARE Group";
                    tailf:cli-full-command;
                    type empty;
                }
                leaf webex-group {
                    tailf:info "WebEx Group";
                    description "WebEx Group";
                    tailf:cli-full-command;
                    type empty;
                }
            }
            container attribute {
                tailf:info "Application attribute to match";
                description "Application attribute to match";
                leaf media-type {
                    tailf:info "Media type attribute to match";
                    description "Media type attribute to match";
                    type enumeration {
                        enum audio {
                            tailf:info "Audio";
                        }
                        enum audio-video {
                            tailf:info "Audio Video";
                        }
                        enum control {
                            tailf:info "Control";
                        }
                        enum data {
                            tailf:info "Data";
                        }
                        enum video {
                            tailf:info "Video";
                        }
                    }
                }
            }
        }
        // class-map * / match access-group
        container access-group {
            tailf:info "Access group";
            description "Access group";
            leaf index {
                tailf:cli-drop-node-name;
                type uint32 {
                    range "1..2699" {
                        tailf:info "<1-2699>;;Access list index";
                    }
                }
            }
            leaf-list name {
                tailf:info "Named Access List";
                description "Named Access List";
                tailf:cli-list-syntax;
                type string {
                    tailf:info "WORD;;Access List name";
                }
            }
        }
        // class-map * / match any
        leaf any {
            tailf:info "Any packets";
            description "Any packets";
            type empty;
        }
        // class-map * / match class-map
        leaf-list class-map {
            tailf:info "Class map";
            description "Class map";
            tailf:cli-list-syntax;
            type leafref {
                path "/ios:native/class-map/name";
                // tailf:info "WORD;;Match class-map name";
            }
        }
        // class-map * / match cos
        leaf-list cos {
            tailf:info "IEEE 802.1Q/ISL class of service/user priority values";
            description "IEEE 802.1Q/ISL class of service/user priority values";
            tailf:cli-flat-list-syntax;
            type uint8 {
                range "0..7";
                tailf:info "<0-7>;;Enter up to 4 class-of-service values"+
                    " separated by white-spaces";
            }
        }
        // class-map * / match destination-address
        container destination-address {
            tailf:info "Destination address";
            description "Destination address";
            leaf-list mac {
                tailf:info "MAC address";
                description "MAC address";
                tailf:cli-list-syntax;
                type yang:mac-address {
                    tailf:info "H.H.H;;MAC address";
                }
            }
        }
        // class-map * / discard-class
        leaf-list discard-class {
            tailf:info "Discard behavior identifier";
            description "Discard behavior identifier";
            tailf:cli-list-syntax;
            type uint8 {
                range "0..7";
                tailf:info "<0-7>;;Discard Class value";
            }
        }
        // class-map * / dscp
        leaf-list dscp {
            tailf:info "Match DSCP in IP(v4) and IPv6 packets";
            description "Match DSCP in IP(v4) and IPv6 packets";
            tailf:cli-flat-list-syntax;
            tailf:cli-list-syntax;
            type dscp-type;
        }
        // class-map * / fr-de
        leaf fr-de {
            tailf:info "Match on Frame-relay DE bit";
            description "Match on Frame-relay DE bit";
            type empty;
        }
        // class-map * / fr-dlci
        leaf-list fr-dlci {
            tailf:info "Match on fr-dlci";
            description "Match on fr-dlci";
            tailf:cli-list-syntax;
            type uint16 {
                range "16..1007";
                tailf:info "<16-1007>;;frame-relay dlci number";
            }
        }
        // class-map * / input-interface
        leaf-list input-interface {
            tailf:info "Select an input interface to match";
            description "Select an input interface to match";
            tailf:cli-list-syntax;
            //FIXME: interface dependency
            type string;
        }
        // class-map * / ip
        container ip {
            tailf:info "IP specific values";
            description "IP specific values";
            // class-map * / ip dscp
            leaf-list dscp {
                tailf:info "Match IP DSCP (DiffServ CodePoints)";
                description "Match IP DSCP (DiffServ CodePoints)";
                tailf:cli-flat-list-syntax;
                tailf:cli-list-syntax;
                type dscp-type;
            }
            // class-map * / ip precedence
            leaf-list precedence {
                tailf:info "Match IP precedence";
                description "Match IP precedence";
                tailf:cli-flat-list-syntax;
                type precedence-type;
            }
            // class-map * / ip rtp
            list rtp {
                tailf:info "Match RTP port nos";
                description "Match RTP port nos";
                key "port1 port2";
                leaf port1 {
                    type uint16 {
                        range "2000..65535";
                        tailf:info "<2000-65535>;;Lower bound of UDP"+
                            " destination port";
                    }
                }
                leaf port2 {
                    type uint16 {
                        range "0..16383";
                        tailf:info "<0-16383>;;Range of UDP ports";
                    }
                }
            }
        }
        // class-map * / non-client-nrt
        leaf non-client-nrt {
            tailf:cli-full-command;
            type empty;
        }
        // class-map * / mpls
        container mpls {
            tailf:info "Multi Protocol Label Switching specific values";
            description "Multi Protocol Label Switching specific values";
            container experimental {
                tailf:info "Match MPLS experimental";
                description "Match MPLS experimental";
                leaf-list topmost {
                    tailf:info "Match MPLS experimental value on topmost label";
                    description "Match MPLS experimental value on topmost label";
                    tailf:cli-flat-list-syntax;
                    type uint8 {
                    range "0..7";
                    tailf:info "<0-7>;;Enter up to 8 experimental values "+
                        "separated by white-spaces";
                    }
                }
            }
        }
        // class-map * / packet
        container packet {
            tailf:info "Layer 3 Packet length";
            description "Layer 3 Packet length";
            container "length" {
                tailf:info "Layer 3 Packet length";
                description "Layer 3 Packet length";
                leaf max {
                    tailf:info "Maximum length of packet";
                    description "Maximum length of packet";
                    type uint16 {
                        range "1..2000";
                        tailf:info "<1-2000>;;Packet length in bytes";
                    }
                }
                leaf min {
                    tailf:info "Minimum length of packet";
                    description "Minimum length of packet";
                    type uint16 {
                        range "1..2000";
                        tailf:info "<1-2000>;;Packet length in bytes";
                    }
                }
            }
        }
        // class-map * / precedence
        leaf-list precedence {
            tailf:info "Match Precedence in IP(v4) and IPv6 packets";
            description "Match Precedence in IP(v4) and IPv6 packets";
            tailf:cli-flat-list-syntax;
            type precedence-type;
        }
        // class-map * / protocol
        container protocol {
            tailf:info "Protocol";
            description "Protocol";
            leaf protocols {
                tailf:cli-drop-node-name;
                type enumeration {
                    enum x802-11-iapp {
                        tailf:info "IEEE 802.11 WLANs WG IAPP";
                    }
                    enum ace-svr {
                        tailf:info "ACE Server/Propagation";
                    }
                    enum aol {
                        tailf:info "America-Online Instant Messenger";
                    }
                    enum appleqtc {
                        tailf:info "Apple QuickTime";
                    }
                    enum biff {
                        tailf:info "Bliff mail notification";
                    }
                    enum bittorrent {
                        tailf:info "bittorrent";
                    }
                    enum bootpc {
                        tailf:info "Bootstrap Protocol Client";
                    }
                    enum bootps {
                        tailf:info "Bootstrap Protocol Server";
                    }
                    enum cddbp {
                        tailf:info "CD Database Protocol";
                    }
                    enum cifs {
                        tailf:info "CIFS";
                    }
                    enum cisco-fna {
                        tailf:info "Cisco FNATIVE";
                    }
                    enum cisco-net-mgmt {
                        tailf:info "cisco-net-mgmt";
                    }
                    enum cisco-svcs {
                        tailf:info "cisco license/perf/GDP/X.25/ident svcs";
                    }
                    enum cisco-sys {
                        tailf:info "Cisco SYSMAINT";
                    }
                    enum cisco-tdp {
                        tailf:info "Cisco TDP";
                    }
                    enum cisco-tna {
                        tailf:info "Cisco TNATIVE";
                    }
                    enum citriximaclient {
                        tailf:info "Citrix IMA Client";
                    }
                    enum clp {
                        tailf:info "Cisco Line Protocol";
                    }
                    enum creativepartnr {
                        tailf:info "Creative Partnr";
                    }
                    enum creativeserver {
                        tailf:info "Creative Server";
                    }
                    enum daytime {
                        tailf:info "Daytime (RFC 867)";
                    }
                    enum dbase {
                        tailf:info "dBASE Unix";
                    }
                    enum dbcontrol_agent {
                        tailf:info "Oracle dbControl Agent po";
                    }
                    enum ddns-v3 {
                        tailf:info "Dynamic DNS Version 3";
                    }
                    enum dhcp-failover {
                        tailf:info "DHCP Failover";
                    }
                    enum directconnect {
                        tailf:info "Direct Connect Version 2.0";
                    }
                    enum discard {
                        tailf:info "Discard port";
                    }
                    enum dnsix {
                        tailf:info "DNSIX Securit Attribute Token Map";
                    }
                    enum echo {
                        tailf:info "Echo port";
                    }
                    enum entrust-svc-hdlr {
                        tailf:info "Entrust KM/Admin Service Handler";
                    }
                    enum entrust-svcs {
                        tailf:info "Entrust sps/aaas/aams";
                    }
                    enum exec {
                        tailf:info "Remote Process Execution";
                    }
                    enum fcip-port {
                        tailf:info "FCIP";
                    }
                    enum ftps {
                        tailf:info "FTP over TLS/SSL";
                    }
                    enum gdoi {
                        tailf:info "GDOI";
                    }
                    enum giop {
                        tailf:info "Oracle GIOP/SSL";
                    }
                    enum gtpv0 {
                        tailf:info "GPRS Tunneling Protocol Version 0";
                    }
                    enum gtpv1 {
                        tailf:info "GPRS Tunneling Protocol Version 1";
                    }
                    enum h225ras {
                        tailf:info "H225 RAS over Unicast";
                    }
                    enum h323callsigalt {
                        tailf:info "h323 Call Signal Alternate";
                    }
                    enum hp-alarm-mgr {
                        tailf:info "HP Performance data alarm manager";
                    }
                    enum hp-collector {
                        tailf:info "HP Performance data collector";
                    }
                    enum hp-managed-node {
                        tailf:info "HP Performance data managed node";
                    }
                    enum hsrp {
                        tailf:info "Hot Standby Router Protocol";
                    }
                    enum https {
                        tailf:info "Secure Hypertext Transfer Protocol";
                    }
                    enum ica {
                        tailf:info "ica (Citrix)";
                    }
                    enum icabrowser {
                        tailf:info "icabrowser (Citrix)";
                    }
                    enum ident {
                        tailf:info "Authentication Service";
                    }
                    enum igmpv3lite {
                        tailf:info "IGMP over UDP for SSM";
                    }
                    enum imap3 {
                        tailf:info "Interactive Mail Access Protocol 3";
                    }
                    enum imaps {
                        tailf:info "IMAP over TLS/SSL";
                    }
                    enum ipass {
                        tailf:info "IPASS";
                    }
                    enum ipsec-msft {
                        tailf:info "Microsoft IPsec NAT-T";
                    }
                    enum irc-serv {
                        tailf:info "IRC-SERV";
                    }
                    enum ircs {
                        tailf:info "IRC over TLS/SSL";
                    }
                    enum ircu {
                        tailf:info "IRCU";
                    }
                    enum isakmp {
                        tailf:info "ISAKMP";
                    }
                    enum iscsi {
                        tailf:info "iSCSI";
                    }
                    enum iscsi-target {
                        tailf:info "iSCSI port";
                    }
                    enum kermit {
                        tailf:info "kermit";
                    }
                    enum ldap-admin {
                        tailf:info "LDAP admin server port";
                    }
                    enum ldaps {
                        tailf:info "LDAP over TLS/SSL";
                    }
                    enum login {
                        tailf:info "Remote login";
                    }
                    enum lotusmtap {
                        tailf:info "Lotus Mail Tracking Agent Protocol";
                    }
                    enum lotusnote {
                        tailf:info "Lotus Note";
                    }
                    // AppNav match protocol
                    enum mapi {
                        tailf:info "MAPI";
                    }
                    enum ms-ad-rep {
                        tailf:info "MS-AD-REP";
                    }
                    enum ms-exch-nspi {
                        tailf:info "MS-EXCH-NSPI";
                    }
                    enum ms-frs {
                        tailf:info "MS-FRS";
                    }
                    enum ms-frsapi {
                        tailf:info "MS-FRSAPI";
                    }
                    enum ms-rfr {
                        tailf:info "MS-RFR";
                    }
                    //ms-sql         MS-SQL
                    enum msn-messenger {
                        tailf:info "MSN-MESSENGER";
                    }
                    enum netlogon {
                        tailf:info "NETLOGON";
                    }
                    enum microsoft-ds {
                        tailf:info "Microsoft-DS";
                    }
                    enum ms-cluster-net {
                        tailf:info "MS Cluster Net";
                    }
                    enum ms-dotnetster {
                        tailf:info "Microsoft .NETster Port";
                    }
                    enum ms-sna {
                        tailf:info "Microsoft SNA Server/Base";
                    }
                    enum ms-sql {
                        tailf:info "Microsoft SQL";
                    }
                    enum ms-sql-m {
                        tailf:info "Microsoft SQL Monitor";
                    }
                    enum msexch-routing {
                        tailf:info "Microsoft Exchange Routing";
                    }
                    enum msnmsgr {
                        tailf:info "MSN Instant Messenger";
                    }
                    enum msrpc {
                        tailf:info "Microsoft Remote Procedure Call";
                    }
                    enum mysql {
                        tailf:info "MySQL";
                    }
                    enum n2h2server {
                        tailf:info "N2H2 Filter Service Port";
                    }
                    enum ncp {
                        tailf:info "NCP (Novell)";
                    }
                    enum net8-cman {
                        tailf:info "Oracle Net8 Cman/Admin";
                    }
                    enum netbios-dgm {
                        tailf:info "NETBIOS Datagram Service";
                    }
                    enum netbios-ns {
                        tailf:info "NETBIOS Name Service";
                    }
                    enum netbios-ssn {
                        tailf:info "NETBIOS Session Service";
                    }
                    enum netstat {
                        tailf:info "Variant of systat";
                    }
                    enum oem-agent {
                        tailf:info "OEM Agent (Oracle)";
                    }
                    enum oracle {
                        tailf:info "Oracle";
                    }
                    enum oracle-em-vp {
                        tailf:info "Oracle EM/VP";
                    }
                    enum oraclenames {
                        tailf:info "Oracle Names";
                    }
                    enum orasrv {
                        tailf:info "Oracle SQL*Net v1/v2";
                    }
                    enum pcanywheredata {
                        tailf:info "pcANYWHEREdata";
                    }
                    enum pcanywherestat {
                        tailf:info "pcANYWHEREstat";
                    }
                    enum pop3s {
                        tailf:info "POP3 over TLS/SSL";
                    }
                    enum pwdgen {
                        tailf:info "Password  Generator Protocol";
                    }
                    enum qmtp {
                        tailf:info "Quick Mail Transfer Protocol";
                    }
                    enum r-winsock {
                        tailf:info "remote-winsock";
                    }
                    enum radius {
                        tailf:info "RADIUS & Accounting";
                    }
                    enum rdb-dbs-disp {
                        tailf:info "Oracle RDB";
                    }
                    enum realmedia {
                        tailf:info "RealNetwork's Realmedia Protocol";
                    }
                    enum realsecure {
                        tailf:info "ISS Real Secure Console Service Port";
                    }
                    enum router {
                        tailf:info "Local Routing Process";
                    }
                    enum rsvp-encap {
                        tailf:info "RSVP ENCAPSULATION-1/2";
                    }
                    enum rsvp_tunnel {
                        tailf:info "RSVP Tunnel";
                    }
                    enum rtc-pm-port {
                        tailf:info "Oracle RTC-PM port";
                    }
                    enum rtelnet {
                        tailf:info "Remote Telnet Service";
                    }
                    enum send {
                        tailf:info "SEND";
                    }
                    enum shell {
                        tailf:info "Remote command";
                    }
                    enum sip-tls {
                        tailf:info "SIP-TLS";
                    }
                    enum sms {
                        tailf:info "SMS RCINFO/XFER/CHAT";
                    }
                    enum snmptrap {
                        tailf:info "SNMP Trap";
                    }
                    enum sql-net {
                        tailf:info "SQL-NET";
                    }
                    enum sqlserv {
                        tailf:info "SQL Services";
                    }
                    enum sqlsrv {
                        tailf:info "SQL Service";
                    }
                    enum sshell {
                        tailf:info "SSLshell";
                    }
                    enum ssp {
                        tailf:info "State Sync Protocol";
                    }
                    enum syslog-conn {
                        tailf:info "Reliable Syslog Service";
                    }
                    enum tacacs {
                        tailf:info "Login Host Protocol (TACACS)";
                    }
                    enum tacacs-ds {
                        tailf:info "TACACS-Database Service";
                    }
                    enum tarantella {
                        tailf:info "Tarantella";
                    }
                    enum tcp {
                        tailf:info "TCP";
                    }
                    enum telnets {
                        tailf:info "Telnet over TLS/SSL";
                    }
                    enum time {
                        tailf:info "Time";
                    }
                    enum timed {
                        tailf:info "Time server";
                    }
                    enum tr-rsrb {
                        tailf:info "cisco RSRB";
                    }
                    enum ttc {
                        tailf:info "Oracle TTC/SSL";
                    }
                    enum udp {
                        tailf:info "UDP";
                    }
                    enum uucp {
                        tailf:info "UUCPD/UUCP-RLOGIN";
                    }
                    enum vqp {
                        tailf:info "VQP";
                    }
                    enum webster {
                        tailf:info "Network Disctionary";
                    }
                    enum who {
                      tailf:info "Who's service";
                    }
                    enum wins {
                      tailf:info "Microsoft WINS";
                    }
                    enum x11 {
                       tailf:info "X Window System";
                    }
                    enum xdmcp {
                      tailf:info "XDM Control Protocol";
                    }
                    enum ymsgr {
                      tailf:info "Yahoo! Instant Messenger";
                    }
                    enum aarp {
                      tailf:info "AppleTalk ARP";
                    }
                    enum appletalk {
                       tailf:info "AppleTalk";
                    }
                    enum arp {
                       tailf:info "IP ARP";
                    }
                    enum bgp {
                      tailf:info "Border Gateway Protocol";
                    }
                    enum bridge {
                        tailf:info "Bridging";
                    }
                    enum bstun {
                        tailf:info "Block Serial Tunnel";
                    }
                    enum cdp {
                        tailf:info "Cisco Discovery Protocol";
                    }
                }
            }
            container citrix {
                tailf:info "Citrix Systems ICA protocol";
                description "Citrix Systems ICA protocol";
                presence "enable citrix system protocol matching";
                leaf ica-tag {
                    tailf:info "Citrix ICA tag 0-high 1-medium 2-low "+
                        "3-background";
                    description "Citrix ICA tag 0-high 1-medium 2-low "+
                        "3-background";
                    type string {
                        tailf:info "WORD;;Enter a string as the sub-protocol "+
                        "parameter";
                    }
                }
            }
            leaf clns {
                tailf:info "ISO CLNS";
                description "ISO CLNS";
                type empty;
            }
            leaf clns_es {
                tailf:info "ISO CLNS End System";
                description "ISO CLNS End System";
                type empty;
            }
            leaf clns_is {
                tailf:info "ISO CLNS Intermediate System";
                description "ISO CLNS Intermediate System";
                type empty;
            }
            leaf cmns {
                tailf:info "ISO CMNS";
                description "ISO CMNS";
                type empty;
            }
            leaf compressedtcp {
                tailf:info "Compressed TCP (VJ";
                description "Compressed TCP (VJ";
                type empty;
            }
            leaf cuseeme {
                tailf:info "CU-SeeMe desktop video conference";
                description "CU-SeeMe desktop video conference";
                type empty;
            }
            leaf decnet {
                tailf:info "DECnet";
                description "DECnet";
                type empty;
            }
            leaf decnet_node {
                tailf:info "DECnet Node";
                description "DECnet Node";
                type empty;
            }
            leaf decnet_router-l1 {
                tailf:info "DECnet Router L1";
                description "DECnet Router L1";
                type empty;
            }
            leaf decnet_router-l2 {
                tailf:info "DECnet Router L2";
                description "DECnet Router L2";
                type empty;
            }
            leaf dhcp {
                tailf:info "Dynamic Host Configuration";
                description "Dynamic Host Configuration";
                type empty;
            }
            leaf dlsw {
                type empty;
                tailf:info "Data Link Switching (Direct encapsulation only";
            }
            leaf dns {
                type empty;
                tailf:info "Domain Name Server lookup";
            }
            leaf edonkey {
                type empty;
                tailf:info "eDonkey";
            }
            leaf egp {
                type empty;
                tailf:info "Exterior Gateway Protocol";
            }
            leaf eigrp {
                type empty;
                tailf:info "Enhanced Interior Gateway Routing Protocol";
            }
            leaf exchange {
                type empty;
                tailf:info "MS-RPC for Exchange";
            }
            container fasttrack {
                tailf:info "FastTrack Traffic - KaZaA, Morpheus, Grokster";
                description "FastTrack Traffic - KaZaA, Morpheus, Grokster";
                presence "enable fasttrack matching";
                leaf file-transfer {
                    tailf:info "File transfer stream";
                    description "File transfer stream";
                    type string {
                        tailf:info "WORD;;Enter a string as the sub-protocol "+
                        "parameter";
                    }
                }
            }
            leaf finger {
                type empty;
                tailf:info "Finger";
            }
            leaf ftp {
                type empty;
                tailf:info "File Transfer Protocol";
            }
            container gnutella {
                tailf:info "Gnutella Version2 Traffic - BearShare, Shareeza, "+
                    "Morpheus";
                description "Gnutella Version2 Traffic - BearShare, Shareeza, "+
                    "Morpheus";
                presence "enable gnutella matching";
                leaf file-transfer {
                    tailf:info "File transfer stream";
                    description "File transfer stream";
                    type string {
                        tailf:info "WORD;;Enter a string as the sub-protocol "+
                            "parameter";
                    }
                }
            }
            leaf gopher {
                type empty;
                tailf:info "Gopher";
            }
            leaf gre {
                type empty;
                tailf:info "Generic Routing Encapsulation";
            }
            leaf h323 {
                type empty;
                tailf:info "H323 Protocol";
            }
            container http {
                tailf:info "World Wide Web traffic";
                description "World Wide Web traffic";
                presence "enable http traffic matching";
                leaf c-header-field {
                tailf:info "Client general Header Field";
                description "Client general Header Field";
                type string {
                    tailf:info "WORD;;Enter a string as the sub-protocol "+
                        "parameter";
                }
            }
            leaf host {
                tailf:info "Server Host Name";
                description "Server Host Name";
                type string {
                    tailf:info "WORD;;Enter a string as the sub-protocol "+
                        "parameter";
                }
            }
            leaf mime {
                tailf:info "Match MIME Type";
                description "Match MIME Type";
                type string {
                    tailf:info "WORD;;Enter a string as the sub-protocol "+
                        "parameter";
                }
            }
            leaf s-header-field {
                tailf:info "Server general Header Field";
                description "Server general Header Field";
                type string {
                    tailf:info "WORD;;Enter a string as the sub-protocol "+
                        "parameter";
                }
            }
            leaf url {
                tailf:info "Match URL String";
                description "Match URL String";
                    type string {
                        tailf:info "WORD;;Enter a string as the sub-protocol "+
                            "parameter";
                    }
                }
            }
            leaf icmp {
                tailf:info "Internet Control Message";
                description "Internet Control Message";
                type empty;
            }
            leaf imap {
                tailf:info "Internet Message Access Protocol";
                description "Internet Message Access Protocol";
                type empty;
            }
            leaf ip {
                tailf:info "IP";
                description "IP";
                type empty;
            }
            leaf ipinip {
                tailf:info "IP in IP (encapsulation";
                description "IP in IP (encapsulation";
                type empty;
            }
            leaf ipsec {
                tailf:info "IP Security Protocol (ESP/AH";
                description "IP Security Protocol (ESP/AH";
                type empty;
            }
            leaf ipv6 {
                tailf:info "IPV6";
                description "IPV6";
                type empty;
            }
            leaf ipx {
                tailf:info "Novell IPX";
                description "Novell IPX";
                type empty;
            }
            leaf irc {
                type empty;
                tailf:info "Internet Relay Chat";
                description "Internet Relay Chat";
            }
            container kazaa2 {
                tailf:info "Kazaa Version 2";
                description "Kazaa Version 2";
                presence "enable kazaa version 2 matching";
                leaf file-transfer {
                    tailf:info "File transfer stream";
                    description "File transfer stream";
                    type string {
                        tailf:info "WORD;;Enter a string as the sub-protocol "+
                            "parameter";
                    }
                }
            }
            leaf kerberos {
                tailf:info "Kerberos";
                description "Kerberos";
                type empty;
            }
            leaf l2tp {
                tailf:info "L2F/L2TP tunnel";
                description "L2F/L2TP tunnel";
                type empty;
            }
            leaf ldap {
                tailf:info "Lightweight Directory Access Protocol";
                description "Lightweight Directory Access Protocol";
                type empty;
            }
            leaf llc2 {
                tailf:info "llc2";
                description "llc2";
                type empty;
            }
            leaf mgcp {
                tailf:info "Media Gateway Control Protocol";
                description "Media Gateway Control Protocol";
                type empty;
            }
            container napster {
                tailf:info "Napster Traffic";
                description "Napster Traffic";
                presence "enable napster matching";
                leaf non-std {
                    tailf:info "Non-standard port advertizements";
                    description "Non-standard port advertizements";
                    type empty;
                }
            }
            leaf netbios {
                tailf:info "NetBIOS";
                description "NetBIOS";
                type empty;
            }
            leaf netshow {
                tailf:info "Microsoft Netshow";
                description "Microsoft Netshow";
                type empty;
            }
            leaf nfs {
                tailf:info "Network File System";
                description "Network File System";
                type empty;
            }
            leaf nntp {
                tailf:info "Network News Transfer Protocol";
                description "Network News Transfer Protocol";
                type empty;
            }
            leaf notes {
                tailf:info "Lotus Notes(R";
                description "Lotus Notes(R";
                type empty;
            }
            leaf novadigm {
                tailf:info "Novadigm EDM";
                description "Novadigm EDM";
                type empty;
            }
            leaf ntp {
                tailf:info "Network Time Protocol";
                description "Network Time Protocol";
                type empty;
            }
            leaf ospf {
                tailf:info "Open Shortest Path First";
                description "Open Shortest Path First";
                type empty;
            }
            leaf pad {
                tailf:info "PAD links";
                description "PAD links";
                type empty;
            }
            leaf pcanywhere {
                tailf:info "Symantec pcANYWHERE";
                description "Symantec pcANYWHERE";
                type empty;
            }
            leaf pop3 {
                tailf:info "Post Office Protocol";
                description "Post Office Protocol";
                type empty;
            }
            leaf pppoe {
                tailf:info "PPP over Ethernet";
                description "PPP over Ethernet";
                type empty;
            }
            leaf pptp {
                tailf:info "Point-to-Point Tunneling Protocol";
                description "Point-to-Point Tunneling Protocol";
                type empty;
            }
            leaf printer {
                tailf:info "print spooler/lpd";
                description "print spooler/lpd";
                type empty;
            }
            leaf qllc {
                tailf:info "qllc protocol";
                description "qllc protocol";
                type empty;
            }
            leaf rcmd {
                tailf:info "BSD r-commands (rsh, rlogin, rexec";
                description "BSD r-commands (rsh, rlogin, rexec";
                type empty;
            }
            leaf rip {
                tailf:info "Routing Information Protocol";
                description "Routing Information Protocol";
                type empty;
            }
            leaf rsrb {
                tailf:info "Remote Source-Route Bridging";
                description "Remote Source-Route Bridging";
                type empty;
            }
            leaf rsvp {
                tailf:info "Resource Reservation Protocol";
                description "Resource Reservation Protocol";
                type empty;
            }
            leaf rtcp {
                tailf:info "Real Time Control Protocol";
                description "Real Time Control Protocol";
                type empty;
            }
            container rtp {
                tailf:info "Real Time Protocol";
                description "Real Time Protocol";
                presence "enable rtp matching";
                leaf audio {
                    tailf:info "Match voice packets";
                    description "Match voice packets";
                    type empty;
                }
                leaf payload-type {
                    tailf:info "Match an explicit PT";
                    description "Match an explicit PT";
                    type string {
                        tailf:info "WORD;;Enter a string as the sub-protocol "+
                                "parameter";
                    }
                }
                leaf video {
                    tailf:info "Match video packets";
                    description "Match video packets";
                    type empty;
                }
            }
            leaf rtsp {
                tailf:info "Real Time Streaming Protocol";
                description "Real Time Streaming Protocol";
                type empty;
            }
            leaf secure-ftp {
                tailf:info "FTP over TLS/SSL";
                description "FTP over TLS/SSL";
                type empty;
            }
            leaf secure-http {
                tailf:info "Secured HTTP";
                description "Secured HTTP";
                type empty;
            }
            leaf secure-imap {
                tailf:info "Internet Message Access Protocol over TLS/SSL";
                description "Internet Message Access Protocol over TLS/SSL";
                type empty;
            }
            leaf secure-irc {
                tailf:info "Internet Relay Chat over TLS/SSL";
                description "Internet Relay Chat over TLS/SSL";
                type empty;
            }
            leaf secure-ldap {
                tailf:info "Lightweight Directory Access Protocol over TLS/SSL";
                description "Lightweight Directory Access Protocol over TLS/SSL";
                type empty;
            }
            leaf secure-nntp {
                tailf:info "Network News Transfer Protocol over TLS/SSL";
                description "Network News Transfer Protocol over TLS/SSL";
                type empty;
            }
            leaf secure-pop3 {
                tailf:info "Post Office Protocol over TLS/SSL";
                description "Post Office Protocol over TLS/SSL";
                type empty;
            }
            leaf secure-telnet {
                tailf:info "Telnet over TLS/SSL";
                description "Telnet over TLS/SSL";
                type empty;
            }
            leaf sip {
                tailf:info "Session Initiation Protocol";
                description "Session Initiation Protocol";
                type empty;
            }
            leaf skinny {
                tailf:info "Skinny Protocol";
                description "Skinny Protocol";
                type empty;
            }
            container smtp {
                tailf:info "Simple Mail Transfer Protocol";
                description "Simple Mail Transfer Protocol";
                leaf extended {
                    type empty;
                }
            }
            leaf snapshot {
                tailf:info "Snapshot routing support";
                description "Snapshot routing support";
                type empty;
            }
            leaf snmp {
                tailf:info "Simple Network Management Protocol";
                description "Simple Network Management Protocol";
                type empty;
            }
            leaf socks {
                tailf:info "SOCKS";
                description "SOCKS";
                type empty;
            }
            leaf sqlnet {
                tailf:info "SQL*NET for Oracle";
                description "SQL*NET for Oracle";
                type empty;
                }
            leaf sqlserver {
                tailf:info "MS SQL Server";
                description "MS SQL Server";
                type empty;
            }
            leaf ssh {
                tailf:info "Secured Shell";
                description "Secured Shell";
                type empty;
            }
            leaf streamwork {
                tailf:info "Xing Technology StreamWorks player";
                description "Xing Technology StreamWorks player";
                type empty;
            }
            leaf stun {
                tailf:info "Serial Tunnel";
                description "Serial Tunnel";
                type empty;
            }
            leaf sunrpc {
                tailf:info "Sun RPC";
                description "Sun RPC";
                type empty;
            }
            leaf syslog {
                tailf:info "WORD;;Enter a string as the sub-protocol "+
                  "parameter";       tailf:info "System Logging Utility";
                description "System Logging Utility";
                type empty;
            }
            leaf telnet {
                tailf:info "Telnet";
                description "Telnet";
                type empty;
            }
            leaf tftp {
                tailf:info "Trivial File Transfer Protocol";
                description "Trivial File Transfer Protocol";
                type empty;
            }
            leaf vdolive {
                tailf:info "VDOLive streaming video";
                description "VDOLive streaming video";
                type empty;
            }
            leaf vofr {
                tailf:info "voice over Frame Relay packets";
                description "voice over Frame Relay packets";
                type empty;
            }
            leaf winmx {
                tailf:info "WinMx file-sharing application";
                description "WinMx file-sharing application";
                type empty;
            }
            leaf xwindows {
                tailf:info "X-Windows remote access";
                description "X-Windows remote access";
                type empty;
            }
        }
        // class-map * / qos-group
        leaf-list qos-group {
            tailf:info "Qos-group";
            description "Qos-group";
            tailf:cli-list-syntax;
            type uint16 {
                tailf:info "<0-99>;;Qos Group value";
                range "0..99";
            }
        }
        // class-map * / match security-group
        container security-group {
            tailf:info "Security group";
            description "Security group";
            container destination {
                tailf:info "Destination security group";
                description "Destination security group";
                leaf tag {
                    tailf:info "Security group tag";
                    description "Security group tag";
                    type uint16 {
                        tailf:info "<1-65533>;;Security group tag id";
                    }
                }
            }
            container source {
                tailf:info "Source security group";
                description "Source security group";
                leaf tag {
                    tailf:info "Security group tag";
                    description "Security group tag";
                    type uint16 {
                        tailf:info "<1-65533>;;Security group tag id";
                    }
                }
            }
        }
        // class-map * / source-address
        container source-address {
            tailf:info "Source address";
            description "Source address";
            leaf-list mac {
                tailf:info "MAC address";
                description "MAC address";
                tailf:cli-list-syntax;
                type yang:mac-address {
                    tailf:info "H.H.H;;MAC address";
                }
            }
        }
        // class-map * / match vlan
        leaf-list vlan {
            tailf:info "VLANs to match";
            description "VLANs to match";
            tailf:cli-range-list-syntax;
            tailf:cli-list-syntax;
            type uint16 {
                tailf:info "<1-4094>;;VLAN id";
                range "1..4094";
            }
        }
    }

    grouping interface-atm-grouping {
        // Removed body
    }

    grouping interface-cellular-grouping {
        //interface * / dialer
        container dialer {
            leaf in-band {
                type empty;
            }
            leaf idle-timeout {
                type uint32;
            }
            leaf string {
                type string;
            }
            leaf watch-group {
                type uint32;
            }
        }
        //interface * / async
        container async {
            leaf mode {
                type enumeration {
                    enum interactive;
                }
            }
        }
    }

    grouping interface-common-grouping {
        // interface * / service-policy
        container service-policy {
            tailf:info "Configure QoS Service Policy";
            description "Configure QoS Service Policy";
            leaf history {
                tailf:cli-full-command;
                tailf:info "Keep history of QoS metrics";
        	    description "Keep history of QoS metrics";
                type empty;
            }
            leaf "input" {
                tailf:cli-full-command;
                tailf:info "Assign policy-map to the input of an interface";
                description "Assign policy-map to the input of an interface";
                type string {
                    tailf:info "WORD;;policy-map name";
                }
                tailf:non-strict-leafref {
                    path "/ios:native/policy-map/name";
                }
            }
            leaf "output" {
                tailf:cli-full-command;
                tailf:info "Assign policy-map to the output of an interface";
                description "Assign policy-map to the output of an interface";
                type string {
                    tailf:info "WORD;;policy-map name";
                }
                tailf:non-strict-leafref {
                    path "/ios:native/policy-map/name";
                }
            }
            container "type" {
                tailf:info "Configure CPL Service Policy";
                description "Configure CPL Service Policy";
                container performance-monitor {
                    tailf:info "Configure media monitor service-policy type";
                    description "Configure media monitor service-policy type";
                    tailf:cli-sequence-commands;
                    tailf:cli-compact-syntax;
                    leaf direction {
                        tailf:cli-drop-node-name;
                        type enumeration {
                            enum "input" {
                                tailf:info "Assign policy-map to the input of an interfcae";
                            }
                            enum "output" {
                                tailf:info "Assign policy-map to the output of an interfcae";
                            }
                        }
                    }
                    leaf name {
                        tailf:cli-drop-node-name;
                        type string {
                            tailf:info "WORD;;policy-map name";
                        }
                        tailf:non-strict-leafref {
                            path "/ios:native/policy-map/name";
                        }
                    }
                }
                // interface * / service-policy type * / service-chain
                container service-chain {
                    tailf:info "Configure Service-chain Service Policy";
                    description "Configure Service-chain Service Policy";
                    tailf:cli-sequence-commands;
                    tailf:cli-compact-syntax;
                    leaf direction {
                        tailf:cli-drop-node-name;
                        type enumeration {
                            enum "input" {
                                tailf:info "Assign policy-map to the input of an interfcae";
                            }
                            enum "output" {
                                tailf:info "Assign policy-map to the output of an interfcae";
                            }
                        }
                    }
                    leaf name {
                        tailf:cli-drop-node-name;
                        type string {
                            tailf:info "WORD;;policy-map name";
                        }
                        tailf:non-strict-leafref {
                            path "/ios:native/policy-map/name";
                        }
                    }
                }
            }
        }
    }

    grouping interface-ethernet-grouping {
        // Removed body
    }

    grouping interface-grouping {
        // Removed body
    }

    grouping interface-overlay-grouping {
        // Removed body
    }

    grouping interface-pointtopoint-grouping {
        // Removed body
    }

    grouping interface-pseudowire-grouping {
        // Removed body
    }

    grouping interface-switch-grouping {
        // Removed body
    }

    grouping interface-tunnel-grouping {
        // Removed body
    }

    grouping interface-zone-member-grouping {
        // interface * / zone-member
        container zone-member {
            tailf:info "Apply zone name";
            description "Apply zone name";
            leaf security {
                tailf:info "Security zone";
                description "Security zone";
                type string;
                tailf:non-strict-leafref {
                    path "/ios:native/zone/security/id";
                }
            }
        }
    }

    grouping police-action-drop-grouping {
        leaf drop {
            tailf:info "drop packet";
            description "drop packet";
            type empty;
        }
    }

    grouping police-action-grouping {
        container actions {
            tailf:cli-break-sequence-commands;
            tailf:cli-no-keyword;
            tailf:cli-drop-node-name;
            tailf:cli-flatten-container;
            // policy-map * / class * / police ? / conform-action
            uses police-conform-action-grouping;
            // policy-map * / class * / police ? / exceed-action
            uses police-exceed-action-grouping;
            // policy-map * / class * / police ? / violate-action
            uses police-violate-action-grouping;
        }
    }

    grouping police-conform-action-grouping {
        container conform-set-clp-transmit {
            tailf:cli-no-keyword;
            tailf:cli-drop-node-name;
            tailf:cli-flatten-container;
            container conform-action {
                tailf:info "action when rate is less than conform burst";
                description "action when rate is less than conform burst";
                tailf:cli-flatten-container;
                leaf set-clp-transmit {
                    tailf:info "set atm clp and send it";
                    description "set atm clp and send it";
                    type empty;
                }
            }
        }
        container conform-set-cos-transmit {
            tailf:cli-no-keyword;
            tailf:cli-drop-node-name;
            tailf:cli-flatten-container;
            container conform-action {
                tailf:info "action when rate is less than conform burst";
                description "action when rate is less than conform burst";
                tailf:cli-flatten-container;
                leaf set-cos-transmit {
                    tailf:info "rewrite packet cos and send it";
                    description "rewrite packet cos and send it";
                    type cos_value-type;
                }
            }
        }
        container conform-set-cos-transmit-table {
            tailf:cli-no-keyword;
            tailf:cli-drop-node-name;
            tailf:cli-flatten-container;
            container conform-action {
                tailf:info "action when rate is less than conform burst";
                description "action when rate is less than conform burst";
                tailf:cli-compact-syntax;
                tailf:cli-flatten-container;
                tailf:cli-sequence-commands;
                leaf set-cos-transmit {
                    tailf:info "rewrite packet cos and send it";
                    description "rewrite packet cos and send it";
                    type cos_value-type;
                }
                leaf table {
                    tailf:info "Specify table-map";
                    description "Specify table-map";
                    type leafref {
                        path "/ios:native/table-map/name";
                    }
                }
            }
        }
        container conform-set-discard-class-transmit {
            tailf:cli-no-keyword;
            tailf:cli-drop-node-name;
            tailf:cli-flatten-container;
            container conform-action {
                tailf:info "action when rate is less than conform burst";
                description "action when rate is less than conform burst";
                tailf:cli-flatten-container;
                leaf set-discard-class-transmit {
                    tailf:info "set discard-class and send it";
                    description "set discard-class and send it";
                    type uint8 {
                        tailf:info "<0-7>;;new discard-class";
                        range "0..7";
                    }
                }
            }
        }
        container conform-set-dscp-transmit {
            tailf:cli-no-keyword;
            tailf:cli-drop-node-name;
            tailf:cli-flatten-container;
            container conform-action {
                tailf:info "action when rate is less than conform burst";
                description "action when rate is less than conform burst";
                tailf:cli-flatten-container;
                leaf set-dscp-transmit {
                    tailf:info "set dscp and send it";
                    description "set dscp and send it";
                    type dscp-type;
                }
            }
        }
        container conform-set-dscp-transmit-table {
            tailf:cli-no-keyword;
            tailf:cli-drop-node-name;
            tailf:cli-flatten-container;
            container conform-action {
                tailf:info "action when rate is less than conform burst";
                description "action when rate is less than conform burst";
                tailf:cli-compact-syntax;
                tailf:cli-flatten-container;
                tailf:cli-sequence-commands;
                leaf set-dscp-transmit {
                    tailf:info "set dscp and send it";
                    description "set dscp and send it";
                    type dscp-type;
                }
                leaf table {
                    tailf:info "Specify table-map";
                    description "Specify table-map";
                    type leafref {
                        path "/ios:native/table-map/name";
                    }
                }
            }
        }
        container conform-set-frde-transmit {
            tailf:cli-no-keyword;
            tailf:cli-drop-node-name;
            tailf:cli-flatten-container;
            container conform-action {
                tailf:info "action when rate is less than conform burst";
                description "action when rate is less than conform burst";
                tailf:cli-flatten-container;
                leaf set-frde-transmit {
                    tailf:info "set FR DE and send it";
                    description "set FR DE and send it";
                    type empty;
                }
            }
        }
        container conform-set-mpls-exp-imposition-transmit {
            tailf:cli-no-keyword;
            tailf:cli-drop-node-name;
            tailf:cli-flatten-container;
            container conform-action {
                tailf:info "action when rate is less than conform burst";
                description "action when rate is less than conform burst";
                tailf:cli-flatten-container;
                leaf set-mpls-exp-imposition-transmit {
                    tailf:info "set exp at tag imposition and send it";
                    description "set exp at tag imposition and send it";
                    type exp_value-type;
                }
            }
        }
        container conform-set-mpls-exp-imposition-transmit-table {
            tailf:cli-no-keyword;
            tailf:cli-drop-node-name;
            tailf:cli-flatten-container;
            container conform-action {
                tailf:info "action when rate is less than conform burst";
                description "action when rate is less than conform burst";
                tailf:cli-compact-syntax;
                tailf:cli-flatten-container;
                tailf:cli-sequence-commands;
                leaf set-mpls-exp-imposition-transmit {
                    tailf:info "set exp at tag imposition and send it";
                        description "set exp at tag imposition and send it";
                        type exp_value-type;
                    }
                leaf table {
                    tailf:info "Specify table-map";
                    description "Specify table-map";
                    type leafref {
                        path "/ios:native/table-map/name";
                    }
                }
            }
        }
        container conform-set-mpls-exp-topmost-transmit {
            tailf:cli-no-keyword;
            tailf:cli-drop-node-name;
            tailf:cli-flatten-container;
            container conform-action {
                tailf:info "action when rate is less than conform burst";
                description "action when rate is less than conform burst";
                tailf:cli-flatten-container;
                leaf set-mpls-exp-topmost-transmit {
                    tailf:info "set exp on topmost label and send it";
                    description "set exp on topmost label and send it";
                    type exp_value-type;
                }
            }
        }
        container conform-set-mpls-exp-topmost-transmit-table {
            tailf:cli-no-keyword;
            tailf:cli-drop-node-name;
            tailf:cli-flatten-container;
            container conform-action {
                tailf:info "action when rate is less than conform burst";
                description "action when rate is less than conform burst";
                tailf:cli-compact-syntax;
                tailf:cli-flatten-container;
                tailf:cli-sequence-commands;
                leaf set-mpls-exp-topmost-transmit {
                    tailf:info "set exp on topmost label and send it";
                    description "set exp on topmost label and send it";
                    type exp_value-type;
                }
                leaf table {
                    tailf:info "Specify table-map";
                    description "Specify table-map";
                    type leafref {
                        path "/ios:native/table-map/name";
                    }
                }
            }
        }
        container conform-set-prec-transmit {
            tailf:cli-no-keyword;
            tailf:cli-drop-node-name;
            tailf:cli-flatten-container;
            container conform-action {
                tailf:info "action when rate is less than conform burst";
                description "action when rate is less than conform burst";
                tailf:cli-flatten-container;
                leaf set-prec-transmit {
                    tailf:info "rewrite packet precedence and send it";
                    description "rewrite packet precedence and send it";
                    type prec_value-type;
                }
            }
        }
        container conform-set-prec-transmit-table {
            tailf:cli-no-keyword;
            tailf:cli-drop-node-name;
            tailf:cli-flatten-container;
            container conform-action {
                tailf:info "action when rate is less than conform burst";
                description "action when rate is less than conform burst";
                tailf:cli-compact-syntax;
                tailf:cli-flatten-container;
                tailf:cli-sequence-commands;
                leaf set-prec-transmit {
                    tailf:info "rewrite packet precedence and send it";
                    description "rewrite packet precedence and send it";
                    type prec_value-type;
                }
                leaf table {
                    tailf:info "Specify table-map";
                    description "Specify table-map";
                    type leafref {
                        path "/ios:native/table-map/name";
                    }
                }
            }
        }
        container conform-set-qos-transmit {
            tailf:cli-no-keyword;
            tailf:cli-drop-node-name;
            tailf:cli-flatten-container;
            container conform-action {
                tailf:info "action when rate is less than conform burst";
                description "action when rate is less than conform burst";
                tailf:cli-flatten-container;
                leaf set-qos-transmit {
                    tailf:info "set qos-group and send it";
                    description "set qos-group and send it";
                    type qos_value-type;
                }
            }
        }
        container conform-set-qos-transmit-table {
        tailf:cli-no-keyword;
        tailf:cli-drop-node-name;
        tailf:cli-flatten-container;
            container conform-action {
                tailf:info "action when rate is less than conform burst";
                description "action when rate is less than conform burst";
                tailf:cli-compact-syntax;
                tailf:cli-flatten-container;
                tailf:cli-sequence-commands;
                leaf set-qos-transmit {
                    tailf:info "set qos-group and send it";
                    description "set qos-group and send it";
                    type qos_value-type;
                }
                leaf table {
                    tailf:info "Specify table-map";
                    description "Specify table-map";
                    type leafref {
                        path "/ios:native/table-map/name";
                    }
                }
            }
        }
        container conform-transmit {
            tailf:cli-no-keyword;
            tailf:cli-drop-node-name;
            tailf:cli-flatten-container;
            container conform-action {
                tailf:info "action when rate is less than conform burst";
                description "action when rate is less than conform burst";
                tailf:cli-flatten-container;
                uses police-action-transmit-grouping;
            }
        }
        container conform-drop {
            tailf:cli-no-keyword;
            tailf:cli-drop-node-name;
            tailf:cli-flatten-container;
            container conform-action {
                tailf:info "action when rate is less than conform burst";
                description "action when rate is less than conform burst";
                tailf:cli-flatten-container;
                uses police-action-drop-grouping;
            }
        }
    }

    grouping police-action-transmit-grouping {
        leaf transmit {
            tailf:info "transmit packet";
            description "transmit packet";
            type empty;
        }
    }

    grouping police-exceed-action-grouping {
        container exceed-dscp {
            tailf:cli-no-keyword;
            tailf:cli-drop-node-name;
            tailf:cli-flatten-container;
            container exceed-action {
                tailf:info "action when rate is within conform and "+
                "conform + exceed burst";
                description "action when rate is within conform and "+
                    "conform + exceed burst";
                tailf:cli-flatten-container;
                leaf dscp {
                    //tailf:info
                    type dscp-type;
                }
            }
        }
        container exceed-set-clp-transmit {
            tailf:cli-no-keyword;
            tailf:cli-drop-node-name;
            tailf:cli-flatten-container;
            container exceed-action {
                tailf:info "action when rate is within conform and "+
                "conform + exceed burst";
                description "action when rate is within conform and "+
                    "conform + exceed burst";
                tailf:cli-flatten-container;
                    leaf set-clp-transmit {
                    tailf:info "set atm clp and send it";
                    description "set atm clp and send it";
                    type empty;
                }
            }
        }
        container exceed-set-cos-transmit {
            tailf:cli-no-keyword;
            tailf:cli-drop-node-name;
            tailf:cli-flatten-container;
            container exceed-action {
                tailf:info "action when rate is within conform and "+
                "conform + exceed burst";
                description "action when rate is within conform and "+
                    "conform + exceed burst";
                tailf:cli-flatten-container;
                leaf set-cos-transmit {
                    tailf:info "rewrite packet cos and send it";
                    description "rewrite packet cos and send it";
                    type cos_value-type;
                }
            }
        }
        container exceed-set-discard-class-transmit {
            tailf:cli-no-keyword;
            tailf:cli-drop-node-name;
            tailf:cli-flatten-container;
            container exceed-action {
                tailf:info "action when rate is within conform and "+
                "conform + exceed burst";
                description "action when rate is within conform and "+
                    "conform + exceed burst";
                tailf:cli-flatten-container;
                leaf set-discard-class-transmit {
                    tailf:info "set discard-class and send it";
                    description "set discard-class and send it";
                    type uint8 {
                        tailf:info "<0-7>;;new discard-class";
                        range "0..7";
                    }
                }
            }
        }
        container exceed-set-dscp-transmit {
            tailf:cli-no-keyword;
            tailf:cli-drop-node-name;
            tailf:cli-flatten-container;
            container exceed-action {
                tailf:info "action when rate is within conform and "+
                "conform + exceed burst";
                description "action when rate is within conform and "+
                    "conform + exceed burst";
                tailf:cli-flatten-container;
                leaf set-dscp-transmit {
                    tailf:info "set dscp and send it";
                    description "set dscp and send it";
                    type dscp-type;
                }
                container set-dscp-transmit-c {
                    tailf:alt-name "set-dscp-transmit";
                    container dscp {
                        leaf table {
                            type enumeration {
                                enum policed-dscp;
                            }
                        }
                    }
                }
            }
        }
        container exceed-set-frde-transmit {
            tailf:cli-no-keyword;
            tailf:cli-drop-node-name;
            tailf:cli-flatten-container;
            container exceed-action {
                tailf:info "action when rate is within conform and "+
                "conform + exceed burst";
                description "action when rate is within conform and "+
                "conform + exceed burst";
                tailf:cli-flatten-container;
                leaf set-frde-transmit {
                    tailf:info "set FR DE and send it";
                    description "set FR DE and send it";
                    type empty;
                }
            }
        }
        container exceed-set-mpls-exp-imposition-transmit {
            tailf:cli-no-keyword;
            tailf:cli-drop-node-name;
            tailf:cli-flatten-container;
            container exceed-action {
                tailf:info "action when rate is within conform and "+
                    "conform + exceed burst";
                description "action when rate is within conform and "+
                    "conform + exceed burst";
                tailf:cli-flatten-container;
                leaf set-mpls-exp-imposition-transmit {
                    tailf:info "set exp at tag imposition and send it";
                    description "set exp at tag imposition and send it";
                    type exp_value-type;
                }
            }
        }
        container exceed-set-mpls-exp-topmost-transmit {
            tailf:cli-no-keyword;
            tailf:cli-drop-node-name;
            tailf:cli-flatten-container;
            container exceed-action {
                tailf:info "action when rate is within conform and "+
                    "conform + exceed burst";
                description "action when rate is within conform and "+
                "conform + exceed burst";
                tailf:cli-flatten-container;
                leaf set-mpls-exp-topmost-transmit {
                    tailf:info "set exp on topmost label and send it";
                    description "set exp on topmost label and send it";
                    type exp_value-type;
                }
            }
        }
        container exceed-set-prec-transmit {
            tailf:cli-no-keyword;
            tailf:cli-drop-node-name;
            tailf:cli-flatten-container;
            container exceed-action {
                tailf:info "action when rate is within conform and "+
                    "conform + exceed burst";
                description "action when rate is within conform and "+
                    "conform + exceed burst";
                tailf:cli-flatten-container;
                leaf set-prec-transmit {
                    tailf:info "rewrite packet precedence and send it";
                    description "rewrite packet precedence and send it";
                    type prec_value-type;
                }
            }
        }
        container exceed-set-qos-transmit {
            tailf:cli-no-keyword;
            tailf:cli-drop-node-name;
            tailf:cli-flatten-container;
            container exceed-action {
                tailf:info "action when rate is within conform and "+
                        "conform + exceed burst";
                description "action when rate is within conform and "+
                        "conform + exceed burst";
                tailf:cli-flatten-container;
                leaf set-qos-transmit {
                    tailf:info "set qos-group and send it";
                    description "set qos-group and send it";
                    type qos_value-type;
                }
            }
        }
        container exceed-transmit {
            tailf:cli-no-keyword;
            tailf:cli-drop-node-name;
            tailf:cli-flatten-container;
            container exceed-action {
                tailf:info "action when rate is within conform and "+
                        "conform + exceed burst";
                description "action when rate is within conform and "+
                        "conform + exceed burst";
                tailf:cli-flatten-container;
                uses police-action-transmit-grouping;
            }
        }
        container exceed-drop {
            tailf:cli-no-keyword;
            tailf:cli-drop-node-name;
            tailf:cli-flatten-container;
            container exceed-action {
                tailf:info "action when rate is within conform and "+
                        "conform + exceed burst";
                description "action when rate is within conform and "+
                        "conform + exceed burst";
                tailf:cli-flatten-container;
                uses police-action-drop-grouping;
            }
        }
    }

    grouping police-violate-action-grouping {
        container violate-set-clp-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                leaf set-clp-transmit {
                  tailf:info "set atm clp and send it";
                  description "set atm clp and send it";
                  type empty;
                }
            }
        }
        container violate-set-cos-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                leaf set-cos-transmit {
                  tailf:info "rewrite packet cos and send it";
                  description "rewrite packet cos and send it";
                  type cos_value-type;
                }
            }
        }
        container violate-set-discard-class-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                leaf set-discard-class-transmit {
                    tailf:info "set discard-class and send it";
                    description "set discard-class and send it";
                    type uint8 {
                        tailf:info "<0-7>;;new discard-class";
                        range "0..7";
                    }
                }
            }
        }
        container violate-set-dscp-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                leaf set-dscp-transmit {
                    tailf:info "set dscp and send it";
                    description "set dscp and send it";
                    type dscp-type;
                }
            }
        }
        container violate-set-frde-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                leaf set-frde-transmit {
                    tailf:info "set FR DE and send it";
                    description "set FR DE and send it";
                    type empty;
                }
            }
        }
        container violate-set-mpls-exp-imposition-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                leaf set-mpls-exp-imposition-transmit {
                    tailf:info "set exp at tag imposition and send it";
                    description "set exp at tag imposition and send it";
                    type exp_value-type;
                }
            }
        }
        container violate-set-mpls-exp-topmost-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                leaf set-mpls-exp-topmost-transmit {
                    tailf:info "set exp on topmost label and send it";
                    description "set exp on topmost label and send it";
                    type exp_value-type;
                }
            }
        }
        container violate-set-prec-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                leaf set-prec-transmit {
                    tailf:info "rewrite packet precedence and send it";
                    description "rewrite packet precedence and send it";
                    type prec_value-type;
                }
            }
        }
        container violate-set-qos-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                leaf set-qos-transmit {
                    tailf:info "set qos-group and send it";
                    description "set qos-group and send it";
                    type qos_value-type;
                }
            }
        }
        container violate-transmit {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                uses police-action-transmit-grouping;
            }
        }
            container violate-drop {
            tailf:cli-no-keyword;
            tailf:cli-drop-node-name;
            tailf:cli-flatten-container;
            container violate-action {
                tailf:info "action when rate is greater than conform + "+
                        "exceed burst";
                description "action when rate is greater than conform + "+
                        "exceed burst";
                tailf:cli-flatten-container;
                uses police-action-drop-grouping;
            }
        }
    }

    grouping pseudowire-grouping {
        // Removed body
    }

    grouping random-detect-grouping {
        leaf min-threshold {
            tailf:cli-drop-node-name;
            tailf:cli-incomplete-command;
            type uint16 {
                range "1..4096";
                tailf:info "<1-4096>;;minimum threshold (number of packets)";
            }
        }
        leaf max-threshold {
            tailf:cli-drop-node-name;
            tailf:cli-incomplete-command;
            type uint16 {
                range "1..4096";
                tailf:info "<1-4096>;;maximum threshold (number of packets)";
            }
        }
        leaf denominator {
            tailf:cli-drop-node-name;
            type uint32 {
                range "1..65535";
                tailf:info "<1-65535>;;mark probability denominator";
            }
        }
    }


/// ========================================================================
/// native
/// ========================================================================

    container native {
        tailf:cli-drop-node-name;
        container table-map {
            tailf:info "Map external entry attributes into routing table";
            tailf:cli-full-command;
            description "Map external entry attributes into routing table";
            tailf:display-when "ipv4 or ../../ipv4 or ../ipv4 " +
                " or ipv6 or ../../ipv6 or ../ipv6 ";
            leaf name {
                description "route-map name";
                tailf:cli-drop-node-name;
                type string {
                    tailf:info "WORD;;route-map name";
                }
            }
            leaf filter {
                tailf:info "Selective route download";
                type empty;
            }
        }

/// ========================================================================
/// interface
/// ========================================================================

    container interface {
        tailf:info "Configure interfaces";
        description "Configure interfaces";
        tailf:cli-diff-dependency "/ios:native/vrf";
        tailf:cli-explicit-exit;

        // interface AppNav-Compress
        list AppNav-Compress {
            tailf:info "Service-Context Virtual Interface Compress";
            description "Service-Context Virtual Interface Compress";
            tailf:cli-allow-join-with-key {
                tailf:cli-display-joined;
            }
            tailf:cli-mode-name "config-if";
            tailf:cli-suppress-key-abbreviation;
            key name;
            leaf name {
                type uint16 {
                    tailf:info "<1-1000>;;AppNav-Compress interface number";
                    range "1..1000";
                }
            }
            uses interface-common-grouping;
        }
        // interface AppNav-UnCompress
        list AppNav-UnCompress {
            tailf:info "Service-Context Virtual Interface UnCompress";
            description "Service-Context Virtual Interface UnCompress";
            tailf:cli-allow-join-with-key {
                tailf:cli-display-joined;
            }
            tailf:cli-mode-name "config-if";
            tailf:cli-suppress-key-abbreviation;
            key name;
            leaf name {
                type uint16 {
                    tailf:info "<1-1000>;;AppNav-UnCompress interface number";
                    range "1..1000";
                }
            }
            uses interface-common-grouping;
        }

        // interface ATM #
        list ATM {
            tailf:info "ATM interface";
            description "ATM interface";
            tailf:cli-allow-join-with-key {
                tailf:cli-display-joined;
            }
            tailf:cli-mode-name "config-if";
            tailf:cli-suppress-key-abbreviation;
            key name;
            leaf name {
                type string {
                    tailf:info "<slot>/<subslot>/<port>;;ATM interface number";
                    pattern "([0-9]/){2}([0-9]|(ima[0-9]))(:[0-9])?";
                }
            }
            uses interface-atm-grouping;
        }

        // subinterface ATM #.#
        container ATM-subinterface {
            tailf:cli-drop-node-name;
            list ATM {
                tailf:cli-allow-join-with-key {
                    tailf:cli-display-joined;
                }
                tailf:cli-mode-name "config-subif";
                tailf:cli-suppress-key-abbreviation;
                key name;
                leaf name {
                    type string {
                        pattern "([0-9]/){2}[0-9]\.([0-9]/){3}[0-9]";
                    }
                }
                uses interface-atm-grouping;
            }
        }

        // interface ATM-ACR #
        list ATM-ACR {
            tailf:info "ATM-ACR interface";
            description "ATM-ACR interface";
            tailf:cli-allow-join-with-key {
                tailf:cli-display-joined;
            }
            tailf:cli-mode-name "config-if";
            tailf:cli-suppress-key-abbreviation;
            key name;
            leaf name {
                type string {
                    tailf:info "<slot>/<subslot>/<port>;;ATM-ACR interface number";
                    pattern "[0-9]";
                }
            }
            uses interface-atm-grouping;
        }

        // subinterface ATM-ACR #.#
        container ATM-ACRsubinterface {
            tailf:cli-drop-node-name;
            list ATM-ACR {
                tailf:cli-allow-join-with-key {
                    tailf:cli-display-joined;
                }
                tailf:cli-mode-name "config-subif";
                tailf:cli-suppress-key-abbreviation;
                key name;
                leaf name {
                    type string {
                        pattern "[0-9]\.([0-9]/){3}[0-9]";
                    }
                }
                uses interface-atm-grouping;
            }
        }
        // interface BDI
        list BDI {
            tailf:info "Bridge-Domain interface";
            description "Bridge-Domain interface";
            tailf:cli-allow-join-with-key {
                tailf:cli-display-joined;
            }
            tailf:cli-mode-name "config-if";
            key name;
            leaf name {
                type string {
                    // pattern "([0-9])+/([0-9])+(/([0-9])+)?";
                    tailf:info "<1-16000>;;BDI interface number";
                }
            }
            uses interface-common-grouping;
        }

        // interface CEM #
        list CEM {
            tailf:info "Circuit Emulation interface";
            description "Circuit Emulation interface";
            tailf:cli-allow-join-with-key {
                tailf:cli-display-joined;
            }
            tailf:cli-mode-name "config-if";
            tailf:cli-suppress-key-abbreviation;
            key name;
            leaf name {
                type string {
                    tailf:info "<slot>/<port>;;CEM interface number";
                    pattern "([0-9]/){2}[0-9]";
                }
            }
            uses interface-atm-grouping;
        }

        // interface CEM-ACR #
        list CEM-ACR {
            tailf:info "Circuit Emulation interface";
            description "Circuit Emulation interface";
            tailf:cli-allow-join-with-key {
                tailf:cli-display-joined;
            }
            tailf:cli-mode-name "config-if";
            tailf:cli-suppress-key-abbreviation;
            key name;
            leaf name {
                type uint8 {
                    tailf:info "<0-255>;;CEM-ACR interface number";
                    range "0..255";
                }
            }
            uses interface-atm-grouping;
        }

        // interface Embedded-Service-Engine
        list Embedded-Service-Engine {
            tailf:info "cisco embedded service engine module";
            description "cisco embedded service engine module";
            tailf:cli-allow-join-with-key {
                tailf:cli-display-joined;
            }
            tailf:cli-mode-name "config-if";
            // tailf:cli-full-command;
            key name;
            leaf name {
                type string {
                    tailf:info "<0-2>/<0-0>;;Embedded-Service-Engine interface number";
                }
            }
            uses interface-common-grouping;
        }

        // interface FastEthernet
        list FastEthernet {
            tailf:info "FastEthernet IEEE 802.3";
            description "FastEthernet IEEE 802.3";
            tailf:cli-allow-join-with-key {
                tailf:cli-display-joined;
            }
            tailf:cli-mode-name "config-if";
                // tailf:cli-full-command;
            key name;
            leaf name {
                type string {
                    //pattern "([0-9])+(/([0-9])+)*";
                    tailf:info "<0-66>/<0-128>;;FastEthernet interface number";
                }
            }
            uses interface-ethernet-grouping;
            uses interface-common-grouping;
            uses interface-zone-member-grouping;
            uses interface-switch-grouping; //CATALYST
        }

        // interface GigabitEthernet
        list GigabitEthernet {
            tailf:info "GigabitEthernet IEEE 802.3z";
            description "GigabitEthernet IEEE 802.3z";
            tailf:cli-allow-join-with-key {
                tailf:cli-display-joined;
            }
            tailf:cli-mode-name "config-if";
                // tailf:cli-full-command;
            key name;
            leaf name {
                type string {
                    //pattern "([0-9])+(/([0-9])+)*";
                    tailf:info "<0-66>/<0-128>;;"+
                        "GigabitEthernet interface number";
                }
            }
            leaf media-type {
                tailf:info "Media type";
                description "Media type";
                type enumeration {
                    enum auto-select {
                        tailf:info "Use whichever connector is attached";
                    }
                    enum rj45 {
                        tailf:info "Copper";
                    }
                    enum sfp {
                        tailf:info "Fiber";
                    }
                }
            }
            leaf port-type {
                //FIXME: tailf:info
                //FIXME: 3600 only?
                type enumeration {
                    enum nni;
                }
            }
            uses interface-ethernet-grouping;
            uses interface-common-grouping;
            uses interface-zone-member-grouping;
            uses interface-switch-grouping; //CATALYST
        }

        // interface TenGigabitEthernet
        list TenGigabitEthernet {
            tailf:info "Ten Gigabit Ethernet";
            description "Ten Gigabit Ethernet";
            tailf:cli-allow-join-with-key {
                tailf:cli-display-joined;
            }
            tailf:cli-mode-name "config-if";
                // tailf:cli-full-command;
            key name;
            leaf name {
                type string {
                    //pattern "([0-9])+(/([0-9])+)*";
                    tailf:info "<0-66>/<0-128>;;"+
                        "TenGigabitEthernet interface number";
                }
            }
            leaf media-type {
                tailf:info "Media type";
                description "Media type";
                type enumeration {
                    enum auto-select {
                        tailf:info "Use whichever connector is attached";
                    }
                    enum rj45 {
                        tailf:info "Copper";
                    }
                        enum sfp {
                        tailf:info "Fiber";
                    }
                }
            }
            leaf port-type {
                //FIXME: tailf:info
                //FIXME: 3600 only?
                type enumeration {
                    enum nni;
                }
            }
            uses interface-ethernet-grouping;
            uses interface-common-grouping;
            uses interface-zone-member-grouping;
            uses interface-switch-grouping; //CATALYST
        }

        // interface Loopback
        list Loopback {
            // pvh hide Loopback interfaces
            //    tailf:hidden full;
            tailf:info "Loopback interface";
            description "Loopback interface";
            tailf:cli-allow-join-with-key {
                tailf:cli-display-joined;
            }
            tailf:cli-mode-name "config-if";
                // tailf:cli-full-command;
            key name;
            leaf name {
                type string {
                    // pattern "([0-9])+/([0-9])+(/([0-9])+)?";
                    tailf:info "<0-2147483647>;;Loopback interface number";
                }
            }
            uses interface-common-grouping;
        }

        list nve {
            tailf:info "Network virtualization endpoint interface";
            description "Network virtualization endpoint interface";
            tailf:cli-allow-join-with-key {
                tailf:cli-display-joined;
            }
            tailf:cli-mode-name "config-if";
            key name;
            leaf name {
                type uint16 {
                    tailf:info "<1-4096>;;nve interface number";
                    range "1..4096";
                }
            }

            container source-interface {
                tailf:info "Specify source interface for NVE";
                description "Specify source interface for NVE";
                // FIXME: tailf:cli-diff-dependency "/ios:native/interface";
                uses interface-grouping;
            }
            container member {
                tailf:cli-incomplete-command;
                tailf:cli-sequence-commands;
                list vni {
                    tailf:info "Configure VNI information";
                    description "Configure VNI information";
                    tailf:cli-sequence-commands;
                    tailf:cli-compact-syntax;

                    key vni-range;
                    leaf vni-range {
                        type string {
                            tailf:info "WORD;;VNI range or instance between 4096-16777215 example: 6010-6030 or 7115";
                        }
                    }
                    container mcast-group {
                        tailf:cli-incomplete-command;
                        tailf:cli-sequence-commands;
                        leaf multicast-group-min {
                            tailf:cli-drop-node-name;
                            tailf:info "Starting Multicast Group IPv4 Address";
                            description "Starting Multicast Group IPv4 Address";
                            type inet:ipv4-address {
                                tailf:info "A.B.C.D;;IP address";
                            }
                        }
                        leaf multicast-group-max {
                            tailf:cli-drop-node-name;
                            tailf:info "Ending Multicast Group IPv4 Address";
                            description "Ending Multicast Group IPv4 Address";
                            type inet:ipv4-address {
                                tailf:info "A.B.C.D;;IP address";
                            }
                        }
                    }
                }
            }
        }

        // interface overlay
        list overlay {
            tailf:info "Overlay interface";
            description "Overlay interface";
            tailf:cli-allow-join-with-key {
                tailf:cli-display-joined;
            }
            tailf:cli-mode-name "config-if";
            key name;
            leaf name {
                type uint16 {
                    tailf:info "<0-512>;;Overlay interface number";
                    range "0..512";
                }
            }
            uses interface-common-grouping;
            uses interface-ethernet-grouping;
            uses interface-overlay-grouping;
        }

        // interface Port-channel
        list Port-channel {
            tailf:info "Ethernet Channel of interfaces";
            description "Ethernet Channel of interfaces";
            tailf:cli-allow-join-with-key {
                tailf:cli-display-joined;
            }
            tailf:cli-mode-name "config-if";
                // tailf:cli-full-command;
            key name;
            leaf name {
                type uint32 {
                    tailf:info "<1-512>;;Port-channel interface number";
                    range "1..512";
                }
            }
            leaf pc-speed {
                tailf:alt-name "speed";
                tailf:info "Configure speed operation.";
                description "Configure speed operation.";
                type enumeration {
                    enum "10" {
                        tailf:info "Force 10 Mbps operation";
                    }
                    enum "100" {
                        tailf:info "Force 100 Mbps operation";
                    }
                    enum "1000" {
                        tailf:info "Enable AUTO speed configuration";
                    }
                    enum "nonegotiate" {
                        //FIXME
                    }
                    enum "auto" {
                        tailf:info "Enable AUTO speed configuration";
                    }
                }
            }
            uses interface-common-grouping;
            uses interface-switch-grouping; //CATALYST
            uses interface-ethernet-grouping;
        }

        // subinterface Port-channel #.#
        container Port-channel-subinterface {
            tailf:cli-drop-node-name;
            list Port-channel {
                tailf:cli-allow-join-with-key {
                    tailf:cli-display-joined;
                }
                tailf:cli-mode-name "config-subif";
                tailf:cli-suppress-key-abbreviation;
                key name;
                leaf name {
                    type string;
                }
                uses interface-common-grouping;
                uses interface-switch-grouping; //CATALYST
                uses interface-ethernet-grouping;
            }
        }

        //interface pseudowire
        list pseudowire {
            tailf:info "Pseudowire Interface";
            description "Pseudowire Interface";
            tailf:cli-mode-name "config-if";
            tailf:cli-allow-join-with-key {
                tailf:cli-display-joined;
            }
            key name;
            leaf name {
                type uint32 {
                    tailf:info "<1-231072>;;pseudowire interface number";
                    range "1..231072";
                }
            }
            uses pseudowire-grouping;
        }
        //interface SM
        list "SM" {
            tailf:info "SM Interface";
            description "SM Interface";
            tailf:cli-mode-name "config-if";
            tailf:cli-allow-join-with-key {
                tailf:cli-display-joined;
            }
            key name;
            leaf name {
                type string {
                    pattern "([0-9])+(/([0-9])+)?";
                }
            }
            uses interface-common-grouping;
        }
        //interface Cellular
        list Cellular {
            tailf:info "Cellular Interface";
            description "Cellular Interface";
            tailf:cli-mode-name "config-if";
            tailf:cli-allow-join-with-key {
                tailf:cli-display-joined;
            }
            key name;
            leaf name {
                type string {
                    pattern "([0-9])+(/([0-9])+)?";
                }
            }
            uses interface-common-grouping;
            uses interface-cellular-grouping;
        }

        // interface Vlan
        list Vlan {
            tailf:info "Catalyst Vlans";
            description "Catalyst Vlans";
            tailf:cli-allow-join-with-key {
                tailf:cli-display-joined;
            }
            key name;
            leaf name {
                type uint16 {
                    tailf:info "<1-4094>;;Vlan interface number";
                    range "1..4094";
                }
            }
            uses interface-common-grouping;
            uses interface-zone-member-grouping;
        }

        // interface Group-Async
        list Group-Async {
            tailf:info "Async Group interface";
            description "Async Group interface";
            tailf:cli-allow-join-with-key {
                tailf:cli-display-joined;
            }
            key name;
            leaf name {
                type uint16 {
                    tailf:info "<0-64>;;Group-Async interface number";
                    range "0..64";
                }
            }
            leaf physical-layer {
                tailf:info "Configure sync or async physical layer on serial "+
                    "interface";
                description "Configure sync or async physical layer on serial "+
                    "interface";
                type enumeration {
                    enum async {
                        tailf:info "Configure asynchronous physical layer on serial "
                        +"interface";
                    }
                    enum sync {
                    tailf:info "Configure synchronous physical layer on serial "+
                        "interface";
                    }
                }
            }
            uses interface-common-grouping;
        }

        // interface Multilink
        list Multilink {
            tailf:info "Multilink-group interface";
            description "Multilink-group interface";
            tailf:cli-allow-join-with-key {
                tailf:cli-display-joined;
            }
            tailf:cli-mode-name "config-if";
            tailf:cli-full-command;
            key name;
            leaf name {
                type uint16 {
                    tailf:info "<1-65535>;;Multilink interface number";
                    range "1..65535";
                }
            }
            uses interface-common-grouping;
            uses interface-pointtopoint-grouping;
        }

        // interface Serial
        list Serial {
            tailf:info "Serial interface";
            description "Serial interface";
            tailf:cli-allow-join-with-key {
                tailf:cli-display-joined;
            }
            tailf:cli-mode-name "config-if";
            tailf:cli-full-command;
            key name;
            leaf name {
                type string {
                    pattern "([0-9])+/([0-9])+/([0-9])+\.([0-9])+/([0-9])+/([0-9])+/([0-9])+:([0-9])";
                    //FIXME: info + syntax
                }
            }
            uses interface-common-grouping;
            uses interface-pointtopoint-grouping;
        }

        // interface Tunnel #
        list Tunnel {
            tailf:info "Tunnel interface";
            description "Tunnel interface";
            tailf:cli-allow-join-with-key {
                tailf:cli-display-joined;
            }
            tailf:cli-mode-name "config-if";
            tailf:cli-suppress-key-abbreviation;
            key name;
            leaf name {
                type uint32 {
                    tailf:info "<0-2147483647>;;Tunnel interface number";
                }
            }
            uses interface-common-grouping;

            // interface Tunnel* / qos
            container qos {
                tailf:info "Quality of Service related commands";
                description "Quality of Service related commands";
                leaf pre-classify {
                    tailf:info "Enable QOS classification before packets are tunnel "+
                        "encapsulated";
                    description "Enable QOS classification before packets are tunnel "+
                        "encapsulated";
                    type empty;
                }
            }

            // interface Tunnel* / tunnel
            uses interface-tunnel-grouping;
        }

        // interface Virtual-Template
        list Virtual-Template {
            tailf:info "Virtual Template interface";
            description "Virtual Template interface";
            tailf:cli-allow-join-with-key {
                tailf:cli-display-joined;
            }
            tailf:cli-mode-name "config-if";
            tailf:cli-full-command;
            tailf:cli-explicit-exit;
            key name;
            leaf name {
                type uint16 {
                    tailf:info "<1-4095>;;Virtual-Template interface number";
                    range "1..4095";
                }
            }
            leaf type {
                tailf:info "type of the virtual-template";
                description "type of the virtual-template";
                tailf:cli-hide-in-submode;
                type enumeration {
                    enum ethernet {
                      tailf:info "Set VT type as ethernet";
                    }
                    enum serial {
                      tailf:info "Set VT type as serial";
                    }
                    enum tunnel {
                      tailf:info "Set VT type as tunnel";
                    }
                    enum vpn {
                      tailf:info "Set VT type as vpn";
                    }
                }
            }

            uses interface-ethernet-grouping;
            uses interface-common-grouping;
            uses interface-zone-member-grouping;
            uses interface-switch-grouping; //CATALYST
            uses interface-pointtopoint-grouping;
            // interface Tunnel* / tunnel
            uses interface-tunnel-grouping;
        }

        // interface VirtualPortGroup
        list VirtualPortGroup {
            tailf:info "Virtual Port Group";
            description "Virtual Port Group";
            tailf:cli-allow-join-with-key {
                tailf:cli-display-joined;
            }
            tailf:cli-mode-name "config-if";
            tailf:cli-full-command;
            tailf:cli-explicit-exit;
            key name;
            leaf name {
                type uint16 {
                    tailf:info " <0-31>;;VirtualPortGroup interface number";
                    range "0..31";
                }
            }
            uses interface-switch-grouping; //CATALYST
            uses interface-ethernet-grouping;
            uses interface-common-grouping;
        }
        // interface vasileft
        list vasileft {
            tailf:info "vasileft";
            description "vasileft";
            tailf:cli-allow-join-with-key {
                tailf:cli-display-joined;
            }
            tailf:cli-mode-name "config-if";
            tailf:cli-full-command;
            tailf:cli-explicit-exit;
            key name;
            leaf name {
                type uint16 {
                    tailf:info "<1-2000>;;vasileft interface number";
                    range "1..2000";
                }
            }
            uses interface-switch-grouping; //CATALYST
            uses interface-ethernet-grouping;
            uses interface-common-grouping;
        }

        // interface vasiright
        list vasiright {
            tailf:info "vasiright";
            description "vasiright";
            tailf:cli-allow-join-with-key {
                tailf:cli-display-joined;
            }
            tailf:cli-mode-name "config-if";
            tailf:cli-full-command;
            tailf:cli-explicit-exit;
            key name;
            leaf name {
                type uint16 {
                    tailf:info "<1-2000>;;vasiright interface number";
                    range "1..2000";
                 }
            }
            uses interface-switch-grouping; //CATALYST
            uses interface-ethernet-grouping;
            uses interface-common-grouping;
        }
    }


/// ========================================================================
/// mls
/// ========================================================================
/// Note: must come before class-map and policy-map.

        container mls {
            tailf:info "mls global commands";
            description "mls global commands";
            tailf:cli-incomplete-no;

            // mls acl
            container acl {
                tailf:info "MLS ACL operation";
                description "MLS ACL operation";
                // mls acl tcam
                container tcam {
                    tailf:info "ACL TCAM";
                    description "ACL TCAM";
                    leaf default-result {
                        tailf:info "Default result to be used during tcam programming";
                        description "Default result to be used during tcam programming";
                        type enumeration {
                            enum bridge {
                                tailf:info "Bridge result";
                            }
                            enum deny {
                                tailf:info "Deny result";
                            }
                            enum permit {
                                tailf:info "Permit result";
                            }
                        }
                    }
                    container log-update {
                        tailf:info "Log TCAM updates";
                        description "Log TCAM updates";
                        presence true;
                        leaf rate-limit-msg {
                            tailf:info "Enable/Disable syslog ratelimiting";
                            description "Enable/Disable syslog ratelimiting";
                            type enumeration {
                                enum disable {
                                    tailf:info "Disable ratelimiting syslog";
                                }
                                enum enable {
                                    tailf:info "Enable syslog ratelimiting at 1 per second";
                                }
                            }
                        }
                    }
                    leaf share-global {
                        tailf:info "share global deny or permit any entries";
                        description "share global deny or permit any entries";
                        tailf:cli-boolean-no;
                        tailf:cli-trim-default;
                        type boolean;
                        default true;
                    }
                }
            }

            //  aging L3 aging
            // mls cef
            container cef {
                tailf:info "cef keyword";
                description "cef keyword";
                container error {
                    leaf action {
                        type enumeration {
                            enum reset;
                        }
                    }
                }
               //  maximum-routes  Configure route allocation for protocols
               //  tunnel          Allow tunnel fragmentation
            }
            //  erm         FIB Exception Recovery Manager
            //  exclude     exclude keyword
            // mls flow
            container flow {
                tailf:info "flowmask keyword";
                description "flowmask keyword";
                leaf ip {
                    tailf:info "flowmask ip keyword";
                    description "flowmask ip keyword";
                    type enumeration {
                        enum interface-destination {
                            tailf:info "interface-destination flow keyword";
                        }
                        enum interface-destination-source {
                            tailf:info "interface-destination-source flow keyword";
                        }
                        enum interface-full {
                            tailf:info "interface-full flow keyword";
                        }
                        enum interface-source {
                            tailf:info "interface-source only flow keyword";
                        }
                    }
                }
            }
            // mls ip
            container ip {
                tailf:info "ip keyword";
                description "ip keyword";
                //  cef        cef keyword
                //  inspect    inspect
                // mls ip multicast
                container multicast {
                    tailf:info "multicast keyword";
                    description "multicast keyword";
                    tailf:cli-display-separated;
                    presence true;
                    //  bidir              Bidir commands
                    //  connected          Enable download of interface/mask entry
                    container consistency-check {
                        tailf:info "Set consistency checking characteristics";
                        description "Set consistency checking characteristics";
                        presence true;
                        leaf settle-time {
                            tailf:info "Settle time for entry/oif for consistancy-checker";
                            description "Settle time for entry/oif for consistancy-checker";
                            type uint16 {
                                tailf:info "<2-3600>;;Settle time for entry/oif in seconds";
                                range "2..3600";
                            }
                        }
                        //  type         Set consistency checker type
                    }
                    //  egress             Set egress replication options
                    leaf flow-stat-timer {
                        tailf:info "timer for flow statistic used by mls-msc and mlsm";
                        description "timer for flow statistic used by mls-msc and mlsm";
                        type uint8 {
                            tailf:info "<1-100>;;#seconds between one batch and another";
                            range "1..100";
                        }
                    }
                    //  met-optimization   Enable or disable met optimisation
                    //  non-rpf            Enable rate-limiting of non-RPF traffic
                    //  replication-mode   Disable auto-detection mode for egress
                    //  sso                Stateful switchover parameters
                    //  threshold          Threshold rate for installing h/w shortcuts
                }
                //  nat        nat keyword
                //  slb        Server Load Balancing
            }
            //  nde         netflow data export (nde) keyword
            //  netflow     netflow keyword
            // mls qos
            container mls-qos-conf {
                tailf:cli-no-keyword;
                tailf:cli-drop-node-name;
                leaf qos {
                    type empty;
                }
            }
            // mls qos
            container qos {
                tailf:info "QoS parameters";
                description "QoS parameters";
                tailf:cli-incomplete-command;
                tailf:cli-incomplete-no;
                // mls qos aggregate-policer *
                list aggregate-policer {
                    tailf:info "Assign aggregate policer";
                    description "Assign aggregate policer";
                    tailf:cli-suppress-mode;
                    tailf:cli-delete-when-empty;
                    tailf:cli-compact-syntax;
                    tailf:cli-sequence-commands {
                        tailf:cli-reset-all-siblings;
                    }
                    key name;
                    leaf name {
                        type string {
                           tailf:info "WORD;;aggregate policer name";
                        }
                    }
                    leaf target-bit-rate {
                        tailf:cli-drop-node-name;
                        type uint64 {
                            tailf:info "<32000-60000000000>;;Target Bit Rate (bits per "
                             +"second) (postfix k, m, g optional; decimal point allowed)";
                            range "32000..60000000000";
                        }
                    }
                    leaf burst-normal {
                        tailf:cli-drop-node-name;
                        tailf:cli-optional-in-sequence;
                        type uint32 {
                         tailf:info "<1000-31250000>;;Normal burst bytes";
                         range "1000..31250000";
                       }
                    }
                    leaf burst-max {
                        tailf:cli-drop-node-name;
                        tailf:cli-optional-in-sequence;
                        when "../burst-normal" {
                            tailf:dependency "../burst-normal";
                        }
                        type uint32 {
                            tailf:info "<1000-31250000>;;Maximum burst bytes";
                            range "1000..31250000";
                        }
                    }
                    leaf pir {
                        tailf:info "PIR";
                        description "PIR";
                        tailf:cli-optional-in-sequence;
                        type uint64 {
                            tailf:info "<32000-60000000000>;;Target Bit Rate (bits per "
                            +"second) (postfix k, m, g optional; decimal point allowed)";
                            range "32000..60000000000";
                        }
                    }
                    container conform-action {
                        tailf:info "action when rate is not exceeded";
                        description "action when rate is not exceeded";
                        tailf:cli-optional-in-sequence;
                        tailf:cli-compact-syntax;
                        tailf:cli-flatten-container;
                        choice action-choice {
                            leaf drop {
                                tailf:info "drop packet";
                                description "drop packet";
                                type empty;
                            }
                            leaf set-dscp-transmit {
                                tailf:info "set dscp and send it";
                                description "set dscp and send it";
                                type dscp-type;
                            }
                            leaf set-mpls-exp-imposition-transmit {
                                tailf:info "set exp at tag imposition and send it";
                                description "set exp at tag imposition and send it";
                                type uint8 {
                                    tailf:info "<0-7>;;new exp";
                                    range "0..7";
                                }
                            }
                            leaf set-prec-transmit {
                                tailf:info "rewrite packet precedence and send it";
                                description "rewrite packet precedence and send it";
                                type uint8 {
                                    tailf:info "<0-7>;;new precedence";
                                    range "0..7";
                                }
                            }
                            leaf transmit {
                                tailf:info "transmit packet";
                                description "transmit packet";
                                type empty;
                            }
                        }
                    }
                    leaf exceed-action {
                        tailf:info "action when rate is exceeded";
                        description "action when rate is exceeded";
                        tailf:cli-optional-in-sequence;
                        type enumeration {
                            enum drop {
                                tailf:info "drop packet";
                            }
                            enum policed-dscp-transmit {
                                tailf:info "change dscp per policed-dscp map and send it";
                            }
                            enum transmit {
                                tailf:info "transmit packet";
                            }
                        }
                    }
                    leaf violate-action {
                        tailf:info "action when rate violated";
                        description "action when rate violated";
                        type enumeration {
                            enum drop {
                                tailf:info "drop packet";
                            }
                            enum policed-dscp-transmit {
                                tailf:info "change dscp per policed-dscp map and send it";
                            }
                            enum transmit {
                                tailf:info "transmit packet";
                            }
                        }
                    }
                }
                //  map                Define QoS mapping
                //  mls qos map
                container map {
                    tailf:info "qos map keyword";
                    description "qos map keyword";
                    leaf-list cos-dscp {
                        tailf:info "cos-dscp map: eight dscp values for cos 0-7";
                        description "cos-dscp map: eight dscp values for cos 0-7";
                        tailf:cli-flat-list-syntax;
                        //max-elements 8;
                        type uint8 {
                            tailf:info "<0-63>;;CoS values separated by spaces (up to 8 values total)";
                            range "0..63";
                        }
                    }
                    leaf-list policed-dscp {
                        tailf:info "policed-dscp map keyword";
                        description  "policed-dscp map keyword";
                        ordered-by user;
                        tailf:cli-flat-list-syntax;
                        type union {
                            type uint8 {
                                tailf:info "<0-63>;;DSCP values separated by spaces (up to 8 values total)";
                                range "0..63";
                            }
                            type enumeration {
                                enum to {
                                    tailf:info "to keyword";
                                }
                            }
                        }
                    }
                }
                //  marking            marking keyword
                //  police             police keyword
                //  protocol           protocol keyword
                //  queueing-only      queueing-only (no QoS rewrite,  no policing)
                //  recirc             recirculate path
                //  mls qos rewrite
                container rewrite {
                    tailf:info "packet qos rewrite enable/disable";
                    description "packet qos rewrite enable/disable";
                    container ip {
                        tailf:info "ip packet qos rewrite enable/disable";
                        description "ip packet qos rewrite enable/disable";
                        container dscp {
                            tailf:info "packet ip dscp rewrite enable/disable";
                            description "packet ip dscp rewrite enable/disable";
                            presence true;
                            leaf slot {
                                tailf:info "slot number";
                                description "slot number";
                                type string {
                                    tailf:info "WORD;;Slots seperated by commas. Valid slots: 1,2,"
                                    +"3,4,5,6,7,8,9";
                                }
                            }
                        }
                    }
                }
                // mls qos queue-set
                container queue-set {
                    tailf:info "Choose a queue set for this queue";
                    description "Choose a queue set for this queue";
                    container output {
                        tailf:info "Direction the command applies for this command";
                        description "Direction the command applies for this command";
                        tailf:cli-sequence-commands;
                        tailf:cli-compact-syntax;
                        leaf queue-set-id {
                            tailf:cli-drop-node-name;
                            type uint8 {
                                tailf:info "<1-2>;;queue-set id";
                                range "1..2";
                            }
                        }
                        list threshold {
                            tailf:info "Assign threshold values to a queue";
                            description "Assign threshold values to a queue";
                            tailf:cli-suppress-mode;
                            tailf:cli-break-sequence-commands;
                            tailf:cli-compact-syntax;
                            tailf:cli-sequence-commands;
                            key queue-id;
                            leaf queue-id {
                                type uint8 {
                                    tailf:info "<1-4>;;enter queue id in this queue set";
                                    range "1..4";
                                }
                            }
                            leaf drop1 {
                                tailf:cli-drop-node-name;
                                description "drop threshold1 1-3200";
                                type uint32 {
                                    tailf:info "<1-3200>;;enter drop threshold1 1-3200";
                                    range "1..3200";
                                }
                            }
                            leaf drop2 {
                                tailf:cli-drop-node-name;
                                description "drop threshold2 1-3200";
                                type uint32 {
                                    tailf:info "<1-3200>;;enter drop threshold2 1-3200";
                                    range "1..3200";
                                }
                            }
                            leaf reserved {
                                tailf:cli-drop-node-name;
                                description "reserved threshold 1-100";
                                type uint32 {
                                    tailf:info "<1-3200>;;enter drop threshold2 1-3200";
                                    range "1..3200";
                                }
                            }
                            leaf maximum {
                                tailf:cli-drop-node-name;
                                description "maximum threshold1 1-3200";
                                type uint32 {
                                    tailf:info "<1-3200>;;enter maximum threshold1 1-3200";
                                    range "1..3200";
                                }
                            }
                        }
                        leaf-list buffers {
                            tailf:info "assign buffers to each egress queue";
                            description "assign buffers to each egress queue";
                            tailf:cli-flat-list-syntax;
                            type uint16 {
                                tailf:info "<0-99>/<1-100>;;enter buffer percentage for queue x 0-99/2 1-100";
                                range "0..100";
                            }
                        }
                    }
                }
                // mls qos srr-queue
                container srr-queue {
                    tailf:info "Configure SRR receive queues";
                    description "Configure SRR receive queues";
                    container input {
                        tailf:info "input keyword";
                        description "input keyword";
                        leaf-list bandwidth {
                            tailf:info "Configure SRR bandwidth";
                            description "Configure SRR bandwidth";
                            tailf:cli-flat-list-syntax;
                            type uint8 {
                                tailf:info "<1-100>;;enter bandwidth weight for queue id x";
                                range "1..100";
                            }
                        }
                        list threshold {
                            tailf:info "Configure queue tail-drop thresholds";
                            description "Configure queue tail-drop thresholds";
                            tailf:cli-suppress-mode;
                            key queue-id;
                            leaf queue-id {
                                type uint8 {
                                    tailf:info "<1-2>;;enter threshold queue id (1-2)";
                                    range "1..2";
                                }
                            }
                            leaf-list queue-size-percent {
                                tailf:cli-drop-node-name;
                                tailf:cli-flat-list-syntax;
                                type uint8 {
                                    tailf:info "<1-100>;;enter percent of queue size for threshold x";
                                    range "1..100";
                                }
                            }
                        }
                        list priority-queue {
                            tailf:info "Configure priority scheduling";
                            description "Configure priority scheduling";
                            tailf:cli-suppress-mode;
                            key queue-number;
                            leaf queue-number {
                                type uint8 {
                                    tailf:info "<1-2>;;enter priority queue number [1-2]";
                                }
                            }
                            leaf bandwidth {
                                tailf:info "ingress priority queue bandwidth % of stack ring";
                                description "ingress priority queue bandwidth % of stack ring";
                                type uint8 {
                                    tailf:info "<0-40>;;enter bandwidth number [0-40]";
                                    range "0..40";
                                }
                            }
                        }
                        list cos-map {
                            tailf:info "Configure cos-map for a queue id";
                            description "Configure cos-map for a queue id";
                            tailf:cli-suppress-mode;
                            key "queue threshold";
                            leaf queue {
                                tailf:info "Assign COS values to a queue";
                                description "Assign COS values to a queue";
                                tailf:cli-expose-key-name;
                                type uint8 {
                                    tailf:info "<1-4>;;enter cos-map output queue id";
                                    range "1..4";
                                }
                            }
                            leaf threshold {
                                tailf:info "Assign COS values to a queue threshold";
                                description "Assign COS values to a queue threshold";
                                tailf:cli-expose-key-name;
                                type uint8 {
                                    tailf:info "<1-3>;;enter cos-map threshold id";
                                    range "1..3";
                                }
                            }
                            leaf-list cos {
                                tailf:cli-drop-node-name;
                                tailf:cli-flat-list-syntax;
                                max-elements 8;
                                type uint8 {
                                    tailf:info "<0-7>;;8 cos values separated by spaces";
                                    range "0..7";
                                }
                            }
                        }
                        list dscp-map {
                            tailf:info "Configure dscp-map for a queue id";
                            description "Configure dscp-map for a queue id";
                            tailf:cli-suppress-mode;
                            key "queue threshold";
                            leaf queue {
                                tailf:info "Assign DSCP values to a queue";
                                description "Assign DSCP values to a queue";
                                tailf:cli-expose-key-name;
                                type uint8 {
                                    tailf:info "<1-4>;;enter dscp-map output queue id";
                                    range "1..4";
                                }
                            }
                            leaf threshold {
                                tailf:info "Assign DSCP values to a queue threshold";
                                description "Assign DSCP values to a queue threshold";
                                tailf:cli-expose-key-name;
                                type uint8 {
                                    tailf:info "<1-3>;;enter dscp-map threshold id";
                                    range "1..3";
                                }
                            }
                            leaf-list dscp {
                                tailf:cli-drop-node-name;
                                tailf:cli-flat-list-syntax;
                                max-elements 8;
                                type uint8 {
                                    tailf:info "<0-63>;;dscp values separated by spaces (up to 8 values total)";
                                    range "0..63";
                                }
                            }
                        }
                    }
                    container output {
                        tailf:info "output keyword";
                        description "output keyword";
                        list cos-map {
                            tailf:info "Configure cos-map for a queue id";
                            description "Configure cos-map for a queue id";
                            tailf:cli-suppress-mode;
                            key "queue threshold";
                            leaf queue {
                                tailf:info "Assign COS values to a queue";
                                description "Assign COS values to a queue";
                                tailf:cli-expose-key-name;
                                type uint8 {
                                    tailf:info "<1-4>;;enter cos-map output queue id";
                                    range "1..4";
                                }
                            }
                            leaf threshold {
                                tailf:info "Assign COS values to a queue threshold";
                                description "Assign COS values to a queue threshold";
                                tailf:cli-expose-key-name;
                                type uint8 {
                                    tailf:info "<1-3>;;enter cos-map threshold id";
                                    range "1..3";
                                }
                            }
                            leaf-list cos {
                                tailf:cli-drop-node-name;
                                tailf:cli-flat-list-syntax;
                                max-elements 8;
                                type uint8 {
                                    tailf:info "<0-7>;;8 cos values separated by spaces";
                                    range "0..7";
                                }
                            }
                        }
                        list dscp-map {
                            tailf:info "Configure dscp-map for a queue id";
                            description "Configure dscp-map for a queue id";
                            tailf:cli-suppress-mode;
                            key "queue threshold";
                            leaf queue {
                                tailf:info "Assign DSCP values to a queue";
                                description "Assign DSCP values to a queue";
                                tailf:cli-expose-key-name;
                                type uint8 {
                                    tailf:info "<1-4>;;enter dscp-map output queue id";
                                    range "1..4";
                                }
                            }
                            leaf threshold {
                                tailf:info "Assign DSCP values to a queue threshold";
                                description "Assign DSCP values to a queue threshold";
                                tailf:cli-expose-key-name;
                                type uint8 {
                                    tailf:info "<1-3>;;enter dscp-map threshold id";
                                    range "1..3";
                                }
                            }
                            leaf-list dscp {
                                tailf:cli-drop-node-name;
                                tailf:cli-flat-list-syntax;
                                max-elements 8;
                                type uint8 {
                                    tailf:info "<0-63>;;dscp values separated by spaces (up to 8 values total)";
                                    range "0..63";
                                }
                            }
                        }
                    }
                }
            }
            //  statistics-export  qos statistics data export
            // mls rate-limit
            container rate-limit {
                tailf:info "Rate limit different behaviors";
                description "Rate limit different behaviors";
                //  all        Rate Limiting for both Unicast and Multicast packets
                container layer2 {
                    tailf:info "layer2 protocol cases";
                    description "layer2 protocol cases";
                    //  ip-admission   IP admission on Layer2 ports
                    container l2pt {
                        tailf:cli-compact-syntax;
                        tailf:cli-sequence-commands {
                            tailf:cli-reset-siblings;
                        }
                        tailf:info "layer2 protocol tunnelling packets";
                        leaf packets-per-second {
                            description "layer2 protocol tunnelling packets";
                            tailf:cli-drop-node-name;
                            type uint32 {
                                 tailf:info "<10-1000000>;;packets per second";
                                 range "10..1000000";
                            }
                        }
                        leaf packets-in-burst {
                            tailf:cli-drop-node-name;
                            type uint32 {
                                tailf:info "<1-255>;;packets in burst";
                                range "1..255";
                            }
                        }
                    }
                    //  mac-security   Mac security traffics
                    container pdu {
                        tailf:info "layer2 protocol data unit packets";
                        description "layer2 protocol data unit packets";
                        tailf:cli-compact-syntax;
                        tailf:cli-sequence-commands {
                            tailf:cli-reset-siblings;
                        }
                        leaf packets-per-second {
                            tailf:cli-drop-node-name;
                            type uint32 {
                               tailf:info "<10-1000000>;;packets per second";
                               range "10..1000000";
                            }
                        }
                        leaf packets-in-burst {
                            tailf:cli-drop-node-name;
                            type uint32 {
                                tailf:info "<1-255>;;packets in burst";
                                range "1..255";
                            }
                        }
                    }
                    //  port-security  Port security traffics
                }
                //  multicast  Rate limiting for Multicast packets
                //  unicast    Rate limiting for Unicast packets
            }
            //  rp          rp
            //  sampling    sampling keyword
            // mls verify
            container verify {
                tailf:info "enable hardware packet parsing error checks";
                description "enable hardware packet parsing error checks";
                container ip {
                    tailf:info "check on IP packets";
                    description "check on IP packets";
                    leaf checksum {
                        tailf:info "check for packet checksum errors";
                        description "check for packet checksum errors";
                        tailf:cli-boolean-no;
                        tailf:cli-trim-default;
                        type boolean;
                        default true;
                    }
                    container "length" {
                       tailf:info "check for packet length errors";
                        description "check for packet length errors";
                        leaf consistent {
                            tailf:info "check length in header against physical frame length";
                            description "check length in header against physical frame length";
                            tailf:cli-boolean-no;
                            tailf:cli-trim-default;
                            type boolean;
                            default true;
                        }
                        leaf minimum {
                            tailf:info "check for minimum packet length";
                            description "check for minimum packet length";
                            tailf:cli-boolean-no;
                            tailf:cli-trim-default;
                            type boolean;
                            default true;
                        }
                    }
                    leaf same-address {
                        tailf:info "check for packet having equal source and destination IP "
                        +"addresses";
                        description "check for packet having equal source and destination IP "
                        +"addresses";
                        type empty;
                    }
                    leaf syslog {
                        tailf:info "syslog packet parse errors";
                        description "syslog packet parse errors";
                        type empty;
                    }
                }
            }
        }

/// ========================================================================
/// policer
/// ========================================================================
// Note: must come before class-map and policy-map.

        container policer {
            tailf:info "Switch policer";
            description "Switch policer";
            // policer aggregate *
            list aggregate {
                tailf:info "Named aggregate policer";
                description "Named aggregate policer";
                tailf:cli-suppress-mode;
                tailf:cli-delete-when-empty;
                tailf:cli-compact-syntax;
                tailf:cli-reset-container;
                tailf:cli-sequence-commands {
                    tailf:cli-reset-siblings;
                }
                key name;
                leaf name {
                    type string {
                        tailf:info "WORD;;aggregate policer Name";
                    }
                }
                // cir <cir-bps>
                leaf cir {
                    tailf:info "Committed information rate";
                    description "Committed information rate";
                    type uint32 {
                        tailf:info "<8000-1000000000>;;Bits per second";
                        range "8000..1000000000";
                    }
                }
                // bc <burst>
                leaf bc {
                    tailf:info "Conform burst";
                    description "Conform burst";
                    tailf:cli-optional-in-sequence;
                    type uint32 {
                        tailf:info "<8000-1000000000>;;Burst bytes";
                        range "8000..1000000000";
                    }
                }
                // conform-action
                leaf conform-action {
                    tailf:info "action when rate is within conform and conform + "+
                        "exceed burst";
                    description "action when rate is within conform and conform + "+
                        "exceed burst";
                    tailf:cli-optional-in-sequence;
                    type empty;
                }
                leaf set-qos-transmit {
                    tailf:info "set qos-group and send it";
                    description "set qos-group and send it";
                    when "../conform-action";
                    tailf:cli-optional-in-sequence;
                    type uint8 {
                        tailf:info "<0-99>;;new qos-group";
                        range "0..99";
                    }
                }
                leaf set-dot1ad-dei-transmit {
                    tailf:info "set dei and send it";
                    description "set dei and send it";
                    when "../conform-action";
                    tailf:cli-optional-in-sequence;
                    type uint8 {
                        tailf:info "<0-1>;;new dei value";
                        range "0..1";
                    }
                }
                leaf set-prec-transmit {
                    tailf:info "rewrite packet precedence and send it";
                    description "rewrite packet precedence and send it";
                    when "../conform-action";
                    tailf:cli-optional-in-sequence;
                    type prec_value-type;
                }
                container set-prec-transmit-table {
                    when "../set-prec-transmit";
                    tailf:cli-no-keyword;
                    tailf:cli-drop-node-name;
                    tailf:cli-optional-in-sequence;
                    tailf:cli-flatten-container;
                    leaf table {
                        tailf:info "Set packet cos from cos based on table map";
                        description "Set packet cos from cos based on table map";
                        tailf:cli-optional-in-sequence;
                        type string;
                        tailf:non-strict-leafref {
                            path "/ios:native/table-map/name";
                        }
                    }
                }
                leaf set-dscp-transmit {
                    tailf:info "set dscp and send it";
                    description "set dscp and send it";
                    when "../conform-action";
                    tailf:cli-optional-in-sequence;
                    type dscp-type;
                }
                container set-dscp-transmit-table {
                    when "../set-dscp-transmit";
                    tailf:cli-no-keyword;
                    tailf:cli-drop-node-name;
                    tailf:cli-optional-in-sequence;
                    tailf:cli-flatten-container;
                    leaf table {
                        tailf:info "Set packet cos from cos based on table map";
                        description "Set packet cos from cos based on table map";
                        tailf:cli-optional-in-sequence;
                        type string;
                        tailf:non-strict-leafref {
                            path "/ios:native/table-map/name";
                        }
                    }
                }
                leaf set-cos-transmit {
                    tailf:info "set cos and send it";
                    description "set cos and send it";
                    when "../conform-action";
                    tailf:cli-optional-in-sequence;
                    type cos_value-type;
                }
                container set-cos-transmit-table {
                    when "../set-cos-transmit";
                    tailf:cli-no-keyword;
                    tailf:cli-drop-node-name;
                    tailf:cli-optional-in-sequence;
                    tailf:cli-flatten-container;
                    leaf table {
                        tailf:info "Set packet cos from cos based on table map";
                        description "Set packet cos from cos based on table map";
                        tailf:cli-optional-in-sequence;
                        type string;
                        tailf:non-strict-leafref {
                            path "/ios:native/table-map/name";
                        }
                    }
                }
                leaf transmit {
                    tailf:info "transmit packet";
                    description "transmit packet";
                    when "../conform-action";
                    tailf:cli-optional-in-sequence;
                    type empty;
                }
                // exceed-action
                leaf exceed-action {
                    tailf:info "action when rate is within conform and conform + "+
                        "exceed burst";
                    description "action when rate is within conform and conform + "+
                        "exceed burst";
                    type empty;
                }
                leaf drop {
                    tailf:info "drop packet";
                    description "drop packet";
                    when "../exceed-action";
                    tailf:cli-optional-in-sequence;
                    tailf:cli-full-command;
                    type empty;
                }
                container exceed-transmit {
                    tailf:cli-no-keyword;
                    tailf:cli-drop-node-name;
                    tailf:cli-optional-in-sequence;
                    tailf:cli-flatten-container;
                    leaf transmit {
                        tailf:info "transmit packet";
                        description "transmit packet";
                        when "../../exceed-action";
                        tailf:cli-optional-in-sequence;
                        type empty;
                    }
                }
            }
        }

/// ========================================================================
/// class-map
/// ========================================================================

        list class-map {
            tailf:info "Configure QoS Class Map";
            description "Configure QoS Class Map";
            tailf:cli-mode-name "config-cmap";
            tailf:cli-suppress-list-no;
            tailf:cli-delete-when-empty;
            tailf:cli-no-key-completion;
            // class-map *
            key name;
            leaf name {
                type string {
                    tailf:info "WORD;;class-map name";
                }
                tailf:cli-disallow-value "type";
            }
            // class-map * type inspect
            leaf "type" {
                tailf:info "type of the class-map";
                description "type of the class-map";
                tailf:cli-prefix-key;
                type enumeration {
                    enum access-control {
        	            tailf:info "access-control specific class-map";
        	        }
                    enum appnav {
                        tailf:info "Configure a APPNAV Class Map";
                    }
                    enum control {
                        tailf:info "Configure a control policy class-map";
                    }
                    enum inspect {
                        tailf:info "Configure Firewall Class Map";
                    }
                    enum multicast-flows {
                        tailf:info "multicast class-maps";
                    }
                    enum stack {
                        tailf:info "class-map for protocol header stack specification";
                    }
                    enum traffic {
                        tailf:info "Configure a subscriber policy traffic classmap";
                    }
                }
            }
            // class-map * <protocol>
            leaf protocol {
                when "../type = 'inspect'";
                tailf:cli-drop-node-name;
                tailf:cli-prefix-key;
                type enumeration {
                    enum aol {
                        tailf:info "Configure CBAC class-map for IM-AOL protocol";
                    }
                    enum edonkey {
                        tailf:info "eDonkey";
                    }
                    enum fasttrack {
                        tailf:info "FastTrack Traffic - KaZaA, Morpheus, Grokster...";
                    }
                    enum gnutella {
                        tailf:info "Gnutella Version2 Traffic - BearShare, Shareeza, "
                        +"Morpheus ...";
                    }
                    enum http {
                        tailf:info "Configure CBAC class-map for HTTP protocol";
                    }
                    enum imap {
                        tailf:info "Configure CBAC class-map for IMAP protocol";
                    }
                    enum kazaa2 {
                        tailf:info "Kazaa Version 2";
                    }
                    enum msnmsgr {
                        tailf:info "Configure CBAC class-map for IM-MSN protocol";
                    }
                    enum pop3 {
                        tailf:info "Configure CBAC class-map for POP3 protocol";
                    }
                    enum smtp {
                        tailf:info "Configure CBAC class-map for SMTP protocol";
                    }
                    enum sunrpc {
                        tailf:info "Configure CBAC class-map for RPC protocol";
                    }
                    enum ymsgr {
                        tailf:info "Configure CBAC class-map for IM-YAHOO protocol";
                    }
                }
            }
            // class-map * <match-any|match-all>
            leaf prematch {
                tailf:cli-no-keyword;
                tailf:cli-prefix-key;
                tailf:cli-drop-node-name;
                type enumeration {
                    enum match-all {
                        tailf:info "Logical-AND all matching statements under "+
                            "this classmap";
                    }
                    enum match-any {
                        tailf:info "Logical-OR all matching statements under this "+
                        "classmap";
                    }
                }
                mandatory true;
            }
            // class-map * / description
            leaf "description" {
                tailf:info "Class-Map description";
                description "Class-Map description";
                tailf:cli-multi-value;
                type string {
                    tailf:info "LINE;;Description of this class-map (up to 200 "+
                          "characters)";
                }
            }
            // class-map * / match
            container match {
                tailf:info "classification criteria";
                description "classification criteria";
                uses class-map-match-grouping;
                uses class-map-appnav-match-grouping;
                container not {
                    tailf:info "Negate this match result";
                    description "Negate this match result";
                    uses class-map-match-grouping;
                    uses class-map-appnav-not-match-grouping;
                }
            }
        }

/// ========================================================================
/// policy-map
/// ========================================================================

        list policy-map {
            tailf:info "Configure QoS Policy Map";
            description "Configure QoS Policy Map";
            tailf:cli-mode-name "config-pmap";
            tailf:cli-diff-dependency "/ios:native/class-map";
            tailf:cli-diff-dependency "/ios:native/table-map";
            tailf:cli-diff-dependency "/ios:native/mls/qos/aggregate-policer";
            tailf:cli-diff-dependency "/ios:native/policer/aggregate";
            key name;
            leaf name {
                type string {
                    tailf:info "WORD;;policy-map name";
                }
                tailf:cli-disallow-value
                "(type)|(http)|(im)|(imap)|(p2p)|(pop3)|(smtp)|(sunrpc)";
            }
            leaf "type" {
                tailf:info "type of the policy-map";
                description "type of the policy-map";
                tailf:cli-prefix-key;
                type enumeration {
                    enum access-control {
                        tailf:info "access-control specific policy-map";
                    }
                    enum appnav {
                        tailf:info "Configure a APPNAV Policy Map";
                    }
                    enum inspect {
                         tailf:info "Configure Firewall Policy Map";
                    }
                    enum packet-service {
                        tailf:info "Configure Packet Service Policy Map";
                    }
                    enum performance-monitor {
                        tailf:info "Performance monitoring policy-map type";
                    }
                    enum service {
                        tailf:info "policymap service configuration";
                    }
                    enum service-chain {
                        tailf:info "Configure Service Chain Policy Map";
                    }
                }
            }
            leaf protocol {
                when "../type = 'inspect'";
                tailf:cli-drop-node-name;
                tailf:cli-prefix-key;
                type enumeration {
                    enum http {
                        tailf:info "Configure CBAC policy-map for HTTP protocol";
                    }
                    enum im {
                        tailf:info "Configure CBAC policy-map for IM protocol";
                    }
                    enum imap {
                        tailf:info "Configure CBAC policy-map for IMAP protocol";
                    }
                    enum p2p {
                        tailf:info "Configure CBAC policy-map for P2P protocols";
                    }
                    enum pop3 {
                        tailf:info "Configure CBAC policy-map for POP3 protocol";
                    }
                    enum smtp {
                        tailf:info "Configure CBAC policy-map for SMTP protocol";
                    }
                    enum sunrpc {
                        tailf:info "Configure CBAC policy-map for RPC protocol";
                    }
                }
            }
            // policy-map * / class *
            list class {
                tailf:info "policy criteria";
                description "policy criteria";
                tailf:cli-mode-name "config-pmap-c";
                key name;
                leaf name {
                    tailf:cli-disallow-value "type";
                    type class-name-type;
                }
                // policy-map * / class * / type
                leaf "type" {
                    tailf:info "type of the class-map";
                    description "type of the class-map";
                    tailf:cli-prefix-key;
                    type enumeration {
                        enum inspect {
                            tailf:info "Configure CBAC Class Map";
                        }
                    }
                }
                leaf insert-before {
                    tailf:info "Insert the class before a specified class";
                    description "Insert the class before a specified class";
                    tailf:cli-hide-in-submode;
                    when "../../type = 'appnav'";
                    type string {
                        tailf:info "WORD;;Insert the class before a specified class";
                    }
                }
                // policy-map * / class * / appnav policy
                container appnav-policy {
                    when "../../type = 'appnav'";
                    tailf:cli-drop-node-name;
                    list distribute {
                        tailf:info "Distribute action";
                        description "Distribute action";
                        tailf:cli-suppress-mode;
                        key service-node-group;
                        leaf service-node-group {
                            tailf:info "Distribute to service-node-group";
                            description "Distribute to service-node-group";
                            tailf:cli-expose-key-name;
                            type string {
                                tailf:info "WORD;;service-node-group name";
                            }
                        }
                        leaf insert-before {
                            tailf:info "Insert before specific node";
                            description "Insert before specific node";
                            tailf:cli-optional-in-sequence;
                            type string {
                                tailf:info "WORD;;service-node-group name";
                            }
                        }
                    }
                    leaf monitor-load {
                        tailf:info "Monitor AO";
                        description "Monitor AO";
                        when "../distribute";
                        type enumeration {
                            enum MS-port-mapper {
                                tailf:info "Monitor Microsoft Endpoint Port Mapper load";
                            }
                            enum cifs {
                                tailf:info "Monitor CIFS Accelerator load";
                            }
                            enum http {
                                tailf:info "Monitor HTTP Accelerator load";
                            }
                            enum ica {
                                tailf:info "Monitor ICA Accelerator load";
                            }
                            enum mapi {
                                tailf:info "Monitor MAPI Accelerator load";
                            }
                            enum nfs {
                                tailf:info "Monitor NFS Accelerator load";
                            }
                            enum ssl {
                                tailf:info "Monitor SSL accelerator load";
                            }
                            enum video {
                                tailf:info "Monitor Video Accelerator load";
                            }
                        }
                    }
                    leaf pass-through {
                        tailf:info "pass-through action";
                        description "pass-through action";
                        type empty;
                    }
                }
                // policy-map * / class * / inspect policy
                container policy {
                    when "../../type = 'inspect'";
                    tailf:cli-drop-node-name;
                    tailf:cli-sequence-commands {
                        tailf:cli-reset-siblings;
                    }
                    leaf action {
                        tailf:cli-drop-node-name;
                        tailf:cli-remove-before-change;
                        type enumeration {
                            enum cxsc {
                                tailf:info "CXSC Inspection";
                            }
                            enum drop {
                                tailf:info "Drop the packet";
                            }
                            enum inspect {
                                tailf:info "Context-based Access Control Engine";
                            }
                            enum pass {
                                tailf:info "Pass the packet";
                            }
                            enum service-policy {
                                tailf:info "Deep Packet Inspection Engine";
                            }
                        }
                    }
                    leaf log {
                        tailf:info "Send logging message for drop or pass";
                        description "Send logging message for drop or pass";
                        when "../action = 'drop'or ../action = 'pass'";
                        type empty;
                    }
                    leaf parameter-map {
                        tailf:cli-drop-node-name;
                        when "../action = 'inspect' or ../action = 'cxsc'";
                        type string;
                        tailf:non-strict-leafref {
                            path "/ios:native/parameter-map/name";
                        }
                    }
                    container dpi {
                        tailf:cli-drop-node-name;
                        when "../action = 'service-policy'";
                        tailf:cli-sequence-commands;
                        tailf:cli-compact-syntax;
                        leaf type {
                            tailf:cli-drop-node-name;
                            type enumeration {
                                enum gtpv0 {
                                    tailf:info "GTPv0 DPI";
                                }
                                enum gtpv1 {
                                    tailf:info "GTPv1 DPI";
                                }
                                enum imap {
                                    tailf:info "IMAP DPI";
                                }
                                enum pop3 {
                                    tailf:info "POP3 DPI";
                                }
                                enum smtp {
                                    tailf:info "SMTP DPI";
                                }
                                enum sunrpc {
                                    tailf:info "RPC DPI";
                                }
                            }
                        }
                        leaf policy-map {
                            tailf:cli-drop-node-name;
                            type string {
                                tailf:info "WORD;;DPI policy-map name";
                            }
                        }
                    }
                }
                // policy-map * / class * / performance-monitor policy
                container pm-policy {
                    when "../../type = 'performance-monitor'";
                        tailf:cli-drop-node-name;
                    container flow {
                        tailf:info "Flow subcommands";
                        description "Flow subcommands";
                        leaf monitor {
                            tailf:info "Apply a Flow Monitor";
                            description "Apply a Flow Monitor";
                            type string {
                                tailf:info "WORD;;Flow monitor name";
                            }
                        }
                    }
                    container monitor {
                        tailf:info "Monitor related parameters";
                        description "Monitor related parameters";
                        container metric {
                            tailf:info "Monitor metric";
                            description "Monitor metric";
                            container rtp {
                                tailf:info "RTP metrics parameters";
                                description "RTP metrics parameters";
                                tailf:cli-add-mode;
                                tailf:cli-mode-name "config-pmap-c-mrtp";
                                list clock-rate {
                                    tailf:info "RTP timestamp field's sampling frequency";
                                    description "RTP timestamp field's sampling frequency";
                                    tailf:cli-suppress-mode;
                                    tailf:cli-sequence-commands;
                                    tailf:cli-compact-syntax;
                                    key number;
                                    leaf number {
                                        type union {
                                            type uint8 {
                                                tailf:info "<0-127>;;payload type number";
                                                range "0..127";
                                            }
                                            type enumeration {
                                                enum celb {
                                                    tailf:info "CELB(25)";
                                                }
                                                enum cn {
                                                    tailf:info "CN(13)";
                                                }
                                                enum default {
                                                    tailf:info "Change the default clock rate for all the dynamic payload type";
                                                }
                                                enum dvi4 {
                                                    tailf:info "DVI4 RFC-3551 8000Hz(5)";
                                                }
                                                enum dvi4-2 {
                                                    tailf:info "DVI4 RFC-3551 16000Hz(6)";
                                                }
                                                enum dvi4-3 {
                                                    tailf:info "DVI4 Dipol 11025Hz(16)";
                                                }
                                                enum dvi4-4 {
                                                    tailf:info "DVI4 Dipol 22050Hz(17)";
                                                }
                                                enum g722 {
                                                    tailf:info "G722(9)";
                                                }
                                                enum g723 {
                                                    tailf:info "G723(4)";
                                                }
                                                enum g728 {
                                                    tailf:info "G728(15)";
                                                }
                                                enum g729 {
                                                    tailf:info "G729(18)";
                                                }
                                                enum gsm {
                                                    tailf:info "GSM(3)";
                                                }
                                                enum h261 {
                                                    tailf:info "H261(31)";
                                                }
                                                enum h263 {
                                                    tailf:info "H263(34)";
                                                }
                                                enum jpeg {
                                                    tailf:info "JPEG(26)";
                                                }
                                                enum l16 {
                                                    tailf:info "L16 channel 1(11)";
                                                }
                                                enum l16-2 {
                                                    tailf:info "L16 channel 2(10)";
                                                }
                                                enum lpc {
                                                    tailf:info "LPC(7)";
                                                }
                                                enum mp2t {
                                                    tailf:info "MP2T(33)";
                                                }
                                                enum mpa {
                                                    tailf:info "MPA(14)";
                                                }
                                                enum mpv {
                                                    tailf:info "MPV(32)";
                                                }
                                                enum nv {
                                                    tailf:info "NV(28)";
                                                }
                                                enum pcma {
                                                    tailf:info "PCMA(8)";
                                                }
                                                enum pcmu {
                                                    tailf:info "PCMU(0)";
                                                }
                                                enum qcelp {
                                                    tailf:info "QCELP(12)";
                                                }
                                            }
                                        }
                                    }
                                    leaf frequency {
                                        tailf:cli-drop-node-name;
                                        type uint32 {
                                            tailf:info "<1000-192000>;;frequency in Hz";
                                            range "1000..192000";
                                        }
                                    }
                                }
                            }
                        }
                    }
                    list react {
                        tailf:info "Configure threshold crossing actions";
                        description "Configure threshold crossing actions";
                        tailf:cli-mode-name "config-pmap-c-react";
                        key id;
                        leaf id {
                            type uint16 {
                                tailf:info "<1-65535>  React instance id";
                            }
                        }
                        leaf mode {
                            tailf:cli-drop-node-name;
                            tailf:cli-hide-in-submode;
                            type enumeration {
                                enum media-stop {
                                    tailf:info "Media stream stopped";
                                }
                                enum  mrv {
                                    tailf:info "Variation in packet rate from configured expected rate";
                                }
                                enum rtp-jitter-average {
                                    tailf:info "Mean jitter for the RTP stream";
                                }
                                enum transport-packets-lost-rate {
                                    tailf:info "Ratio of lost packets to total reaceived packets";
                                }
                            }
                        }
                        leaf description {
                            tailf:info "Description for threshold crossing action instance";
                            description "Description for the instance";
                            tailf:cli-multi-value;
                            type string;
                        }
                        container action {
                            tailf:info "Config react action";
                            description "Config react action";
                            leaf snmp {
                                tailf:info "SNMP is notified of the event";
                                description "SNMP is notified of the event";
                                tailf:cli-full-command;
                                type empty;
                            }
                            leaf syslog {
                                tailf:info "The threshold-crossing event is logged to syslog";
                                description "The threshold-crossing event is logged to syslog";
                                tailf:cli-full-command;
                                type empty;
                             }
                        }
                        container alarm {
                            tailf:info "Config react alarm";
                            description "Config react alarm";
                            leaf severity {
                                tailf:info "Alarm severity - default level none";
                                description "Alarm severity - default level none";
                                type enumeration {
                                    enum alert {
                                        tailf:info "TCA severity level critical (severity = 2)";
                                    }
                                    enum critical {
                                        tailf:info "TCA severity level major (severity = 3)";
                                    }
                                    enum emergency {
                                        tailf:info "TCA severity level critical (severity = 1)";
                                    }
                                    enum error {
                                        tailf:info "TCA severity level minor (severity = 4)";
                                    }
                                    enum info {
                                        tailf:info "TCA severity level default (severity = 5)";
                                    }
                                }
                            }
                            container type {
                                tailf:info "Alarm raised type - for each flow or a group";
                                description "Alarm raised type - for each flow or a group";
                                leaf discrete {
                                    tailf:info "Alert for each flow within the class";
                                    description "Alert for each flow within the class";
                                    tailf:cli-full-command;
                                    type empty;
                                }
                                container grouped {
                                    tailf:info "Alert if more than one flow cross the threshold";
                                    description "Alert if more than one flow cross the threshold";
                                    leaf count {
                                        tailf:info "Number of flows in the group cross the threshold";
                                        description "Number of flows in the group cross the threshold";
                                        tailf:cli-full-command;
                                        type uint16 {
                                            tailf:info "<1-65535>;;Number of flows";
                                        }
                                    }
                                   leaf percent {
                                        tailf:info "Percent of flows in the group cross the threshold";
                                        description "Percent of flows in the group cross the threshold";
                                        tailf:cli-full-command;
                                        type uint8 {
                                            tailf:info "<1-100>;;Percent of flows";
                                            range "1..100";
                                        }
                                    }
                                }
                            }
                        }
                        container threshold {
                            tailf:info "Config react threshold";
                            description "Config react threshold";
                            container value {
                                tailf:info "Range of percentage loss that would trigger the alarm";
                                description "Range of percentage loss that would trigger the alarm";
                                leaf ge {
                                    tailf:info "greater and equal to";
                                    description "greater and equal to";
                                    tailf:cli-full-command;
                                    type string {
                                        tailf:info "WORD;;rtp lost fraction threshold 0.05 - 100 (% in precision of 0.01)";
                                    }
                                }
                                leaf gt {
                                    tailf:info "greater than";
                                    description "greater than";
                                    tailf:cli-full-command;
                                    type string {
                                        tailf:info "WORD;;rtp lost fraction threshold 0.05 - 100 (% in precision of 0.01)";
                                    }
                                }
                                leaf le {
                                    tailf:info "less and equal to";
                                    description "less and equal to";
                                    tailf:cli-full-command;
                                    type string {
                                        tailf:info "WORD;;rtp lost fraction threshold 0.05 - 100 (% in precision of 0.01)";
                                    }
                                }
                                leaf lt {
                                    tailf:info "less than";
                                    description "less than";
                                    tailf:cli-full-command;
                                    type string {
                                        tailf:info "WORD;;rtp lost fraction threshold 0.05 - 100 (% in precision of 0.01)";
                                    }
                                }
                                container range {
                                    tailf:info "threshold within the range of";
                                    description "threshold within the range of";
                                    tailf:cli-sequence-commands;
                                    tailf:cli-compact-syntax;
                                    leaf low {
                                        tailf:cli-drop-node-name;
                                        type string {
                                            tailf:info "WORD;;rtp lost fraction threshold 0.05 - 100 (% in precision of 0.01)";
                                        }
                                    }
                                    leaf high {
                                        tailf:cli-drop-node-name;
                                        type string {
                                            tailf:info "WORD;;rtp lost fraction threshold 0.05 - 100 (% in precision of 0.01)";
                                        }
                                    }
                                }
                            }
                        }
                    }
                }
                // policy-map * / class * / inspect-police
                container inspect-police {
                    when "../policy/action = 'inspect'";
                    tailf:cli-drop-node-name;
                    container police {
                        tailf:info "Police";
                        description "Police";
                        tailf:cli-sequence-commands {
                            tailf:cli-reset-siblings;
                        }
                        tailf:cli-compact-syntax;
                        leaf rate {
                            tailf:info "Specify police rate";
                            description "Specify police rate";
                            type uint32 {
                                tailf:info "<8000-2000000000>;;Rate value in bps";
                                range "8000..2000000000";
                            }
                        }
                        leaf burst {
                            tailf:info "Specify 'burst' parameter";
                            description "Specify 'burst' parameter";
                            type uint32 {
                                tailf:info "<1000-512000000>;;Burst value in bytes";
                                range "1000..512000000";
                            }
                        }
                    }
                }
                list action-list {
                    tailf:cli-drop-node-name;
                    tailf:cli-suppress-mode;
                    key action-type;
                    ordered-by user;
                    leaf action-type {
                        type policy-action-type;
                    }
                    choice action-param {
                        case bandwidth-case {
                            // policy-map * / class * / bandwidth
                            container bandwidth {
                                //tailf:info "Bandwidth";
                                tailf:cli-drop-node-name;
                                when "../action-type = 'bandwidth'";
                                leaf bits {
                                    tailf:cli-drop-node-name;
                                    type uint32 {
                                        range "8..2000000";
                                        tailf:info "<8-2000000>;;Kilo Bits per second";
                                    }
                                }
                                leaf percent {
                                    tailf:info "% of total Bandwidth";
                                    description "% of total Bandwidth";
                                    type percentage-type;
                                }
                                container remaining {
                                    tailf:info "% of the remaining bandwidth";
                                    description "% of the remaining bandwidth";
                                    leaf percent {
                                        tailf:info "% of the remaining bandwidth";
                                        description "% of the remaining bandwidth";
                                        type percentage-type;
                                    }
                                    leaf ratio {
                                        tailf:info "ratio for sharing excess bandwidth";
                                        description "ratio for sharing excess bandwidth";
                                        type uint16 {
                                            tailf:info "<1-65536>;;Ratio";
                                        }
                                    }
                                }
                            }
                        }
                        case compression-case {
                            // policy-map * / class * / compression
                            container compression {
                                //tailf:info "Activate Compression";
                                tailf:cli-drop-node-name;
                                //presence "Activate Compression";
                                when "../action-type = 'compression'";
                                container header {
                                    tailf:info "configure header compression";
                                    description "configure header compression";
                                    presence "configure header compression";
                                    leaf ip {
                                        tailf:info "configure ip header compression";
                                        description "configure ip header compression";
                                        type enumeration {
                                            enum rtp {
                                                tailf:code-name "header_rtp";
                                                tailf:info "configure rtp header compression";
                                            }
                                            enum tcp {
                                                tailf:info "configure tcp header compression";
                                            }
                                        }
                                    }
                                }
                            }
                        }
                        //case drop-case {
                            // policy-map * / class * / drop
                            //leaf drop {
                                //tailf:info "Drop all packets";
                                // tailf:cli-full-command;
                                //type empty;
                            //}
                        //}
                        case estimate-case {
                            // policy-map * / class * / estimate
                            container estimate {
                                //tailf:info "estimate resources required for this class";
                                tailf:cli-drop-node-name;
                                when "../action-type = 'estimate'";
                                container bandwidth {
                                    presence "bandwidth required to service this class";
                                    tailf:info "bandwidth required to service this class";
                                    description "bandwidth required to service this class";
                                    tailf:cli-sequence-commands;
                                    tailf:cli-compact-syntax;
                                    container delay-one-in {
                                        tailf:info "specify QoS target delay";
                                        description "specify QoS target delay";
                                        tailf:cli-compact-syntax;
                                        tailf:cli-sequence-commands;
                                        leaf doi {
                                            tailf:cli-drop-node-name;
                                            tailf:cli-incomplete-command;
                                            type uint32 {
                                                range "50..1000000";
                                                tailf:info "<50-1000000>;;delay one packet "+
                                                    "of N";
                                            }
                                        }
                                        leaf milliseconds {
                                            type uint32 {
                                                range "8..1000" {
                                                    tailf:info "<8-1000>;;worst-case "+
                                                        "milliseconds of delay";
                                                }
                                            }
                                        }
                                    }
                                    leaf drop-one-in {
                                        tailf:info "specify QoS target loss rate";
                                        description "specify QoS target loss rate";
                                        type uint32 {
                                            tailf:info "<50-1000000>;;drop one packet of N";
                                        }
                                    }
                                }
                            }
                        }
                        case forward-case {
                            //policy-map * / class * / forward service-path
                            container forward {
                                //tailf:info "forward service-path action";
                                tailf:cli-reset-container;
                                tailf:cli-drop-node-name;
                                when "../action-type = 'forward'";
                                list service-path {
                                    tailf:info "Service Path Entries";
                                    description "Service Path Entries";
                                    tailf:cli-suppress-mode;
                                    key "service-path-id";
                                    leaf service-path-id {
                                        type uint32 {
                                            range "0..16777215";
                                            tailf:info "<0-16777215>;;Service Path ID";
                                        }
                                    }
                                    leaf service-index {
                                        tailf:info "Service Index";
                                        description "Service Index";
                                        type uint8 {
                                            range "2..255";
                                            tailf:info "<2-255>;;Service Index ID";
                                        }
                                    }
                                }
                            }
                        }
                        case fair-queue-case {
                            // policy-map * / class * / fair-queue
                            // class-default: fair-queue [number-of-dynamic-queues]
                            // DWFQ: fair-queue
                            // policy-map: fair-queue [queue-limit queue-value]
                            // NOT SUPPORTED:
                            // air-queue [congestive-discard-threshold [dynamic-q [reservable-q]]]
                            container fair-queue {
                                //tailf:info "Enable Flow-based Fair Queuing in this Class";
                                tailf:cli-reset-container;
                                tailf:cli-drop-node-name;
                                when "../action-type = 'fair-queue'";
                                leaf dynamic-queues {
                                    tailf:cli-drop-node-name;
                                    tailf:cli-full-command;
                                    type uint32 {
                                        range "16|32|64|128|256|512|1024|2048|4096" {
                                        tailf:info "<16-4096>;;Number Dynamic Conversation "+
                                            "Queues";
                                        }
                                    }
                                }
                                leaf queue-limit {
                                    tailf:info "per flow queue limit";
                                    description "per flow queue limit";
                                    tailf:cli-full-command;
                                    type uint16 {
                                        tailf:info "<1-32768>;;packets";
                                        range "1..32768";
                                    }
                                }
                            }
                        }
                        case netflow-sampler-case {
                            // policy-map * / class * / netflow-sampler
                            leaf netflow-sampler {
                                //tailf:info "NetFlow action";
                                tailf:cli-drop-node-name;
                                tailf:cli-full-command;
                                when "../action-type = 'netflow-sampler'";
                                // should be leafref to sampler
                                type string {
                                    tailf:info "WORD;;Name of the flow sampler";
                                }
                            }
                        }
                        case police-case {
                            // policy-map * / class * / police ?
                            choice police-choice {
                                // policy-map * / class * / police aggregate
                                case police-aggregate-case {
                                    container police-aggregate {
                                        tailf:cli-no-keyword;
                                        tailf:cli-drop-node-name;
                                        container police {
                                            //tailf:info "Police";
                                            tailf:cli-drop-node-name;
                                            when "../../action-type = 'police'" {
                                                tailf:dependency "../../action-type";
                                            }
                                            leaf aggregate {
                                                tailf:info "Choose aggregate policer for current class";
                                                description "Choose aggregate policer for current class";
                                                type string {
                                                    tailf:info "WORD;;enter aggregate-policer name";
                                                }
                                            }
                                        }
                                    }
                                }
                                // police (policy-map)
                                // police cir <bps> [[bc <burst-normal>] [be <burst-max>]]
                                //        [pir <bps> [be <burst-bytes>]] ACTIONS
                                // NOTE: cir, bc & be keywords are mandatory in this model.
                                //       Java code will add missing cir,bc and be in show().
                                case police-policy-map-case {
                                    container police-policy-map {
                                        tailf:cli-no-keyword;
                                        tailf:cli-drop-node-name;
                                        container police {
                                            tailf:cli-add-mode;
                                            tailf:cli-mode-name "config-pmap-c-police";
                                            tailf:cli-flatten-container;
                                            tailf:cli-sequence-commands {
                                                tailf:cli-reset-siblings;
                                            }
                                            tailf:cli-drop-node-name;
                                            when "../../action-type = 'police'" {
                                                tailf:dependency "../../action-type";
                                            }
                                            // cir <bps>
                                            leaf cir {
                                                tailf:info "Committed information rate";
                                                description "Committed information rate";
                                                tailf:cli-hide-in-submode;
                                                type police-bps-type;
                                            }
                                            // [bc <burst-normal>]
                                            leaf bc {
                                                tailf:info "Conform burst";
                                                description "Conform burst";
                                                tailf:cli-optional-in-sequence;
                                                tailf:cli-hide-in-submode;
                                                type police-burst-type;
                                            }
                                            // [be <burst-max>]
                                            leaf be {
                                                when "../bc";
                                                tailf:info "Excess burst";
                                                description "Excess burst";
                                                tailf:cli-optional-in-sequence;
                                                tailf:cli-hide-in-submode;
                                                type police-burst-type;
                                            }
                                             // [pir <bps> [be <burst-bytes>]]
                                            leaf pir {
                                                tailf:info "Peak Information Rate";
                                                description "Peak Information Rate";
                                                tailf:cli-optional-in-sequence;
                                                tailf:cli-hide-in-submode;
                                                type police-bps-type;
                                            }
                                            container pir-be {
                                                when "../pir";
                                                tailf:cli-no-keyword;
                                                tailf:cli-drop-node-name;
                                                tailf:cli-optional-in-sequence;
                                                tailf:cli-flatten-container;
                                                tailf:cli-hide-in-submode;
                                                leaf be {
                                                    tailf:info "Excess burst";
                                                    description "Excess burst";
                                                    type police-burst-type;
                                                }
                                            }
                                            // conform-action | exceed-action | violate-action
                                            uses police-action-grouping;
                                        }
                                    }
                                }
                                // police cir percent (combo of percent & policy-map versions)
                                // police cir percent <percentage>
                                //    [bc] <burst> ms] [be [<burst> ms]
                                //    [pir percent <percentage> [be <burst> ms]] ACTIONS
                                case police-cir-percent-case {
                                    container police-cir-percent {
                                        tailf:cli-no-keyword;
                                        tailf:cli-drop-node-name;
                                        container police {
                                            tailf:cli-drop-node-name;
                                            when "../../action-type = 'police'" {
                                                tailf:dependency "../../action-type";
                                            }
                                            container cir {
                                                tailf:info "Committed information rate";
                                                description "Committed information rate";
                                                container percent {
                                                    tailf:info "% of interface bandwidth for Committed "+
                                                     "information rate";
                                                    description "% of interface bandwidth for Committed "+
                                                    "information rate";
                                                    tailf:cli-add-mode;
                                                    tailf:cli-mode-name "config-pmap-c-police";
                                                    tailf:cli-incomplete-command;
                                                    tailf:cli-flatten-container;
                                                    tailf:cli-sequence-commands {
                                                        tailf:cli-reset-siblings;
                                                    }
                                                    // percent <percentage>
                                                    leaf percentage {
                                                        tailf:cli-drop-node-name;
                                                        tailf:cli-hide-in-submode;
                                                        type percentage-type;
                                                    }
                                                    // [bc <burst> ms]
                                                    leaf bc {
                                                        tailf:info "Conform burst";
                                                        description "Conform burst";
                                                        tailf:cli-optional-in-sequence;
                                                        tailf:cli-hide-in-submode;
                                                        type uint16 {
                                                            tailf:info "<1-2000>;;Burst ms";
                                                        }
                                                    }
                                                    container bc-ms {
                                                        when "../bc";
                                                        tailf:cli-no-keyword;
                                                        tailf:cli-drop-node-name;
                                                        tailf:cli-optional-in-sequence;
                                                        tailf:cli-hide-in-submode;
                                                        tailf:cli-compact-syntax;
                                                        tailf:cli-flatten-container;
                                                        leaf ms {
                                                            tailf:info "Milli seconds";
                                                            description "Milli seconds";
                                                            tailf:cli-no-keyword;
                                                            type empty;
                                                        }
                                                    }
                                                    // [be [<burst> ms]
                                                    leaf be {
                                                        when "../bc-ms/ms" {
                                                            tailf:dependency "../bc-ms/ms";
                                                        }
                                                        tailf:info "Excess burst";
                                                        tailf:cli-optional-in-sequence;
                                                        tailf:cli-hide-in-submode;
                                                        type uint16 {
                                                            tailf:info "<1-2000>;;Burst ms";
                                                        }
                                                    }
                                                    container be-ms {
                                                        when "../be";
                                                        tailf:cli-no-keyword;
                                                        tailf:cli-drop-node-name;
                                                        tailf:cli-hide-in-submode;
                                                        tailf:cli-compact-syntax;
                                                        tailf:cli-flatten-container;
                                                        leaf ms {
                                                            tailf:info "Milli seconds";
                                                            description "Milli seconds";
                                                            tailf:cli-no-keyword;
                                                            type empty;
                                                        }
                                                    }
                                                    // [pir percent <percentage> [be <burst> ms]]
                                                    container pir {
                                                        tailf:info "Peak Information Rate";
                                                        description "Peak Information Rate";
                                                        tailf:cli-compact-syntax;
                                                        tailf:cli-flatten-container;
                                                        tailf:cli-hide-in-submode;
                                                        tailf:cli-optional-in-sequence;
                                                        leaf percent {
                                                            tailf:info "% of interface bandwidth for Peak "+
                                                                "Information Rate";
                                                            description "% of interface bandwidth for Peak "+
                                                                "Information Rate";
                                                            type percentage-type;
                                                        }
                                                    }
                                                    container pir-be {
                                                        when "../pir";
                                                        tailf:cli-no-keyword;
                                                        tailf:cli-drop-node-name;
                                                        tailf:cli-optional-in-sequence;
                                                        tailf:cli-flatten-container;
                                                        tailf:cli-hide-in-submode;
                                                        leaf be {
                                                            tailf:info "Excess burst";
                                                            description "Excess burst";
                                                            type uint16 {
                                                                tailf:info "<1-2000>;;Burst ms";
                                                            }
                                                        }
                                                    }
                                                    container pir-be-ms {
                                                        when "../pir-be/be" {
                                                           tailf:dependency "../pir-be/be";
                                                        }
                                                        tailf:cli-no-keyword;
                                                        tailf:cli-drop-node-name;
                                                        tailf:cli-optional-in-sequence;
                                                        tailf:cli-hide-in-submode;
                                                        tailf:cli-flatten-container;
                                                        leaf ms {
                                                            tailf:info "Milli seconds";
                                                            description "Milli seconds";
                                                            tailf:cli-no-keyword;
                                                            type empty;
                                                        }
                                                    }
                                                    // conform-action | exceed-action | violate-action
                                                    uses police-action-grouping;
                                                }
                                            }
                                        }
                                    }
                                }
                                // police rate (control-plane)
                                // police rate <units> <pps|bps> [burst <burst-in-x> <packets|bytes>]
                                //   [peak-rate <peak-rate-in-xps> <pps|bps>]
                                //   [peak-burst <peak-burst-in-x> <packets|bytes>]
                                //   [conform-action <action>]
                                case police-rate-unit-case {
                                    container police-rate-unit {
                                        tailf:cli-no-keyword;
                                        tailf:cli-drop-node-name;
                                        container police {
                                            tailf:cli-drop-node-name;
                                            when "../../action-type = 'police'" {
                                                tailf:dependency "../../action-type";
                                            }
                                            container rate {
                                                tailf:info "Specify police rate";
                                                description "Specify police rate";
                                                tailf:cli-add-mode;
                                                tailf:cli-mode-name "config-pmap-c-police";
                                                tailf:cli-flatten-container;
                                                tailf:cli-sequence-commands {
                                                    tailf:cli-reset-siblings;
                                                }
                                                // <units>
                                                leaf "units" {
                                                    tailf:cli-drop-node-name;
                                                    tailf:cli-hide-in-submode;
                                                    type uint64 {
                                                    tailf:info "<1-2000000000>;;Rate value in the range "+
                                                         "8000-2,000,000,000 bps or 1-2,000,000 pps";
                                                    }
                                                }
                                                // <pps|bps>
                                                leaf xps {
                                                    tailf:cli-no-keyword;
                                                    tailf:cli-drop-node-name;
                                                    tailf:cli-hide-in-submode;
                                                    type police-pps-bps-type;
                                                }
                                                // [burst <burst-in-x> <packets|bytes>]
                                                container burst {
                                                    tailf:info "Specify 'burst' parameter";
                                                    description "Specify 'burst' parameter";
                                                    tailf:cli-optional-in-sequence;
                                                    tailf:cli-compact-syntax;
                                                    tailf:cli-hide-in-submode;
                                                    tailf:cli-flatten-container;
                                                    tailf:cli-sequence-commands;
                                                    leaf burst-value {
                                                        tailf:cli-no-keyword;
                                                        tailf:cli-drop-node-name;
                                                        tailf:cli-incomplete-command;
                                                        type uint32 {
                                                            tailf:info "<1-512000000>;;Burst value in "+
                                                                "packets/bytes";
                                                        }
                                                    }
                                                    leaf burst-type {
                                                        tailf:cli-no-keyword;
                                                        tailf:cli-drop-node-name;
                                                        tailf:cli-hide-in-submode;
                                                        type police-packets-bytes-type;
                                                    }
                                                }
                                                // [peak-rate <peak-rate-in-xps> <pps|bps>]
                                                container peak-rate {
                                                    tailf:info "Specify peak rate";
                                                    description "Specify peak rate";
                                                    tailf:cli-optional-in-sequence;
                                                    tailf:cli-compact-syntax;
                                                    tailf:cli-flatten-container;
                                                    tailf:cli-hide-in-submode;
                                                    tailf:cli-sequence-commands;
                                                    leaf peak-rate-value {
                                                        tailf:cli-no-keyword;
                                                        tailf:cli-drop-node-name;
                                                        tailf:cli-incomplete-command;
                                                        type uint32 {
                                                            tailf:info "<1-512000000>;;Peak-rate value in "+
                                                                "packets or bytes per second";
                                                            range "1..512000000";
                                                        }
                                                    }
                                                    leaf xps {
                                                        tailf:cli-no-keyword;
                                                        tailf:cli-drop-node-name;
                                                        type police-pps-bps-type;
                                                    }
                                                }
                                                // [peak-burst <peak-burst-in-x> <packets|bytes>]
                                                container peak-burst {
                                                    tailf:info "Specify 'peak-burst' parameter for peak-rate";
                                                    description "Specify 'peak-burst' parameter for peak-rate";
                                                    tailf:cli-optional-in-sequence;
                                                    tailf:cli-compact-syntax;
                                                    tailf:cli-flatten-container;
                                                    tailf:cli-hide-in-submode;
                                                    tailf:cli-sequence-commands;
                                                    leaf burst-value {
                                                        tailf:cli-no-keyword;
                                                        tailf:cli-drop-node-name;
                                                        tailf:cli-incomplete-command;
                                                        type uint32 {
                                                            tailf:info "<1-512000000>;;Burst value in "+
                                                                "packets/bytes";
                                                        }
                                                    }
                                                    leaf burst-type {
                                                        tailf:cli-no-keyword;
                                                        tailf:cli-drop-node-name;
                                                        type police-packets-bytes-type;
                                                    }
                                                }
                                                // conform-action | exceed-action | violate-action
                                                uses police-action-grouping;
                                            }
                                        }
                                    }
                                }
                                // police rate percent (control-plane)
                                // police rate percent <percentage> [burst <ms> ms]
                                //    [peak-rate percent <percentage>] [peak-burst <ms> ms]
                                case police-rate-percent-case {
                                    container police-rate-percent {
                                        tailf:cli-no-keyword;
                                        tailf:cli-drop-node-name;
                                        container police {
                                            tailf:cli-drop-node-name;
                                            when "../../action-type = 'police'" {
                                                tailf:dependency "../../action-type";
                                            }
                                            container rate {
                                                tailf:info "Specify police rate";
                                                description "Specify police rate";
                                                container percent {
                                                    tailf:info "% of interface bandwidth for rate";
                                                    description "% of interface bandwidth for rate";
                                                    tailf:cli-add-mode;
                                                    tailf:cli-mode-name "config-pmap-c-police";
                                                    tailf:cli-flatten-container;
                                                    tailf:cli-sequence-commands {
                                                        tailf:cli-reset-siblings;
                                                    }
                                                    // <percentage>
                                                    leaf percentage {
                                                        tailf:cli-drop-node-name;
                                                        tailf:cli-hide-in-submode;
                                                        type percentage-type;
                                                    }
                                                    // [burst <ms> ms]
                                                    leaf burst {
                                                        tailf:info "Specify 'burst' parameter";
                                                        description "Specify 'burst' parameter";
                                                        tailf:cli-optional-in-sequence;
                                                        tailf:cli-hide-in-submode;
                                                        type uint16 {
                                                            tailf:info "<1-2000>;;Burst value in milliseconds";
                                                        }
                                                    }
                                                    leaf ms {
                                                        when "../burst";
                                                        tailf:info "Treat 'burst' value in milliseconds";
                                                        description "Treat 'burst' value in milliseconds";
                                                        tailf:cli-hide-in-submode;
                                                        type empty;
                                                    }
                                                    // [peak-rate percent <percentage>]
                                                    container peak-rate {
                                                        tailf:info "Specify peak rate";
                                                        description "Specify peak rate";
                                                        tailf:cli-hide-in-submode;
                                                        tailf:cli-optional-in-sequence;
                                                        tailf:cli-flatten-container;
                                                        leaf percent {
                                                            tailf:info "% of interface bandwidth for peak-rate";
                                                            description "% of interface bandwidth for peak-rate";
                                                            type percentage-type;
                                                        }
                                                    }
                                                    // [peak-burst <ms> ms]
                                                    leaf peak-burst {
                                                        tailf:info "Specify 'peak-burst' parameter for "+
                                                            "'peak-rate'";
                                                        description "Specify 'peak-burst' parameter for "+
                                                            "'peak-rate'";
                                                        tailf:cli-hide-in-submode;
                                                        tailf:cli-optional-in-sequence;
                                                        type uint16 {
                                                            tailf:info "<1-2000>;;Peak burst value in "+
                                                                "milliseconds";
                                                        }
                                                    }
                                                    container peak-burst-ms {
                                                        when "../peak-burst";
                                                        tailf:cli-no-keyword;
                                                        tailf:cli-drop-node-name;
                                                        tailf:cli-optional-in-sequence;
                                                        tailf:cli-hide-in-submode;
                                                        tailf:cli-flatten-container;
                                                        leaf ms {
                                                            tailf:info "Milli seconds";
                                                            description "Milli seconds";
                                                            tailf:cli-no-keyword;
                                                            type empty;
                                                        }
                                                    }
                                                    // conform-action | exceed-action | violate-action
                                                    uses police-action-grouping;
                                                }
                                            }
                                        }
                                    }
                                }
                                // police rate pdp
                                // police rate pdp [burst <bytes>]
                                //    [peak-rate pdp [peak-burst <bytes>]] ACTIONS
                                case police-rate-pdp-case {
                                    container police-rate-pdp {
                                        tailf:cli-no-keyword;
                                        tailf:cli-drop-node-name;
                                        container police {
                                            tailf:cli-drop-node-name;
                                            when "../../action-type = 'police'" {
                                                tailf:dependency "../../action-type";
                                            }
                                            container rate {
                                                tailf:info "Specify police rate";
                                                description "Specify police rate";
                                                container pdp {
                                                    tailf:info "% of interface bandwidth for rate";
                                                    description "% of interface bandwidth for rate";
                                                    tailf:cli-add-mode;
                                                    tailf:cli-mode-name "config-pmap-c-police";
                                                    tailf:cli-flatten-container;
                                                    tailf:cli-sequence-commands {
                                                        tailf:cli-reset-siblings;
                                                    }
                                                    // [burst <bytes>]
                                                    leaf burst {
                                                        tailf:info "Conform burst";
                                                        description "Conform burst";
                                                        tailf:cli-hide-in-submode;
                                                        tailf:cli-optional-in-sequence;
                                                        type police-burst-type;
                                                    }
                                                    // [peak-rate pdp [peak-burst <bytes>]]
                                                    leaf peak-rate {
                                                        tailf:info "Specify peak rate";
                                                        description "Specify peak rate";
                                                        tailf:cli-hide-in-submode;
                                                        tailf:cli-optional-in-sequence;
                                                        type enumeration {
                                                            enum "pdp" {
                                                            }
                                                        }
                                                    }
                                                    leaf peak-burst {
                                                        when "../peak-rate";
                                                        tailf:info "Specify 'peak-burst' parameter for "+
                                                            "'peak-rate'";
                                                        description "Specify 'peak-burst' parameter for "+
                                                            "'peak-rate'";
                                                        tailf:cli-hide-in-submode;
                                                        tailf:cli-optional-in-sequence;
                                                        type police-burst-type;
                                                    }
                                                    // conform-action | exceed-action | violate-action
                                                    uses police-action-grouping;
                                                }
                                            }
                                        }
                                    }
                                }
                                // police target-bit-rate  <bits per second>
                                case police-target-bitrate-case {
                                    container police-target-bitrate {
                                    tailf:cli-no-keyword;
                                    tailf:cli-drop-node-name;
                                    container police {
                                        tailf:cli-drop-node-name;
                                        when "../../action-type = 'police'" {
                                            tailf:dependency "../../action-type";
                                        }
                                        tailf:cli-add-mode;
                                        tailf:cli-mode-name "config-pmap-c-police";
                                        leaf bit-rate {
                                             tailf:info "Target bit rate (bits per second) (postfix k, m, g optional),
                                                 decimal point allowed";
                                             description "Target bit rate (bits per second) (postfix k, m, g optional),
                                                 decimal point allowed";
                                                 tailf:cli-no-keyword;
                                                 tailf:cli-drop-node-name;
                                                 tailf:cli-hide-in-submode;
                                                 type uint64 {
                                                     tailf:info "<8000-10000000000>;;Target bit rate (bits per second)";
                                                     range "8000..10000000000";
                                                 }
                                             }
                                             // conform-action | exceed-action | violate-action
                                             uses police-action-grouping;
                                        }
                                    }
                                }
                                // police flow (policy-map)
                                // police flow [mask {dest-only | full-flow | src-only}]
                                //    <bps> [<burst-normal>] ACTIONS
                                case police-flow-case {
                                    container police-flow {
                                    tailf:cli-no-keyword;
                                    tailf:cli-drop-node-name;
                                    container police {
                                        tailf:cli-drop-node-name;
                                        when "../../action-type = 'police'" {
                                            tailf:dependency "../../action-type";
                                        }
                                        container flow {
                                            tailf:info "police each flow";
                                            description "police each flow";
                                            tailf:cli-add-mode;
                                            tailf:cli-mode-name "config-pmap-c-police";
                                            tailf:cli-flatten-container;
                                            tailf:cli-sequence-commands {
                                                tailf:cli-reset-siblings;
                                            }
                                            // [mask {dest-only | full-flow | src-only}]
                                            leaf mask {
                                                tailf:info "flow mask to be used for policing";
                                                description "flow mask to be used for policing";
                                                tailf:cli-hide-in-submode;
                                                tailf:cli-optional-in-sequence;
                                                type enumeration {
                                                    enum dest-only {
                                                        tailf:info "destination-address only flow mask";
                                                    }
                                                    enum full-flow {
                                                        tailf:info "full flow mask";
                                                    }
                                                    enum src-only {
                                                        tailf:info "source-address only flow mask";
                                                    }
                                                }
                                            }
                                            // <bps>
                                            leaf bps {
                                                tailf:cli-drop-node-name;
                                                tailf:cli-hide-in-submode;
                                                type police-bps-type;
                                            }
                                            // [<burst-normal>]
                                            leaf burst-normal {
                                                when "../bps";
                                                tailf:cli-drop-node-name;
                                                tailf:cli-hide-in-submode;
                                                tailf:cli-optional-in-sequence;
                                                type police-burst-type;
                                            }
                                            // conform-action | exceed-action | violate-action
                                            uses police-action-grouping;
                                            }
                                        }
                                    }
                                }
                                // police (Catalyst 4500)
                                // police <bps> bps <byte> byte ACTIONS
                                case police-catalyst-case {
                                    container police-catalyst {
                                        tailf:cli-no-keyword;
                                        tailf:cli-drop-node-name;
                                        container police {
                                            tailf:cli-add-mode;
                                            tailf:cli-mode-name "config-pmap-c-police";
                                            tailf:cli-flatten-container;
                                            tailf:cli-drop-node-name;
                                            when "../../action-type = 'police'" {
                                                tailf:dependency "../../action-type";
                                            }
                                            tailf:cli-sequence-commands {
                                                tailf:cli-reset-siblings;
                                            }
                                            // <bps> bps
                                            leaf bps-value {
                                                tailf:cli-no-keyword;
                                                tailf:cli-drop-node-name;
                                                tailf:cli-hide-in-submode;
                                                tailf:cli-incomplete-command;
                                                type string {
                                                    tailf:info "<32000-32000000000>;;Rate in bits per second "+
                                                        "(postfix k, m, g optional; decimal point allowed)";
                                                }
                                            }
                                            leaf bps {
                                                tailf:cli-hide-in-submode;
                                                tailf:cli-incomplete-command;
                                                type empty;
                                            }
                                            // <byte> byte
                                            leaf byte-value {
                                                tailf:cli-no-keyword;
                                                tailf:cli-drop-node-name;
                                                tailf:cli-hide-in-submode;
                                                tailf:cli-incomplete-command;
                                                type string {
                                                    tailf:info "<32000-32000000000>;;(postfix k, m, g "+
                                                        "optional; decimal point allowed)";
                                                }
                                            }
                                            leaf byte {
                                                tailf:cli-hide-in-submode;
                                                type empty;
                                            }
                                            // conform-action | exceed-action | violate-action
                                            container actions {
                                                tailf:cli-no-keyword;
                                                tailf:cli-break-sequence-commands;
                                                tailf:cli-drop-node-name;
                                                tailf:cli-flatten-container;
                                                tailf:cli-hide-in-submode;
                                                // policy-map * / class * / police ? / conform-action
                                                uses police-conform-action-grouping;
                                                // policy-map * / class * / police ? / exceed-action
                                                uses police-exceed-action-grouping;
                                                // policy-map * / class * / police ? / violate-action
                                                uses police-violate-action-grouping;
                                            }
                                        }
                                    }
                                }
                                // police (Catalyst C3550)
                                // police <bps> <burst> exceed-action {drop | policed-dscp-transmit}]
                                case police-switch-case {
                                    container police-switch {
                                        tailf:cli-no-keyword;
                                        tailf:cli-drop-node-name;
                                        container police {
                                            tailf:cli-compact-syntax;
                                            tailf:cli-drop-node-name;
                                            when "../../action-type = 'police'" {
                                                tailf:dependency "../../action-type";
                                            }
                                            tailf:cli-sequence-commands {
                                                tailf:cli-reset-siblings;
                                            }
                                            // <cir>
                                            leaf cir {
                                                tailf:cli-incomplete-command;
                                                tailf:cli-drop-node-name;
                                                type uint32 {
                                                    tailf:info "<8000-1000000000>;;Bits per second";
                                                    range "8000..1000000000";
                                                }
                                            }
                                            // <bc>
                                            leaf bc {
                                                tailf:cli-drop-node-name;
                                                type uint32 {
                                                    tailf:info "<8000-2000000>;;Normal burst bytes";
                                                    range "8000..2000000";
                                                }
                                            }
                                            // exceed-action
                                            leaf exceed-action {
                                                tailf:info "action when rate is exceeded";
                                                description "action when rate is exceeded";
                                                type enumeration {
                                                    enum drop {
                                                        tailf:info "drop packet";
                                                    }
                                                    enum policed-dscp-transmit {
                                                        tailf:info "change dscp per policed-dscp map and send it";
                                                    }
                                                }
                                            }
                                        }
                                    }
                                }
                            }
                        }
                        case priority-case {
                            // policy-map * / class * / priority
                            container priority {
                                //tailf:info "Strict Scheduling Priority for this Class";
                                tailf:cli-compact-syntax;
                                tailf:cli-sequence-commands;
                                tailf:cli-drop-node-name;
                                when "../action-type = 'priority'";
                                leaf level {
                                    tailf:info "Multi-Level Priority Queue";
                                    description "Multi-Level Priority Queue";
                                    tailf:cli-optional-in-sequence;
                                    type uint8 {
                                        tailf:info "<1-2>;;Multi-Level Priority Queue";
                                        range "1..2";
                                    }
                                }
                                choice priority-type {
                                    leaf kilo-bits {
                                        tailf:cli-drop-node-name;
                                        type uint32 {
                                            range "8..2000000";
                                            tailf:info "<8-2000000>;;Kilo Bits per second";
                                        }
                                    }
                                    leaf percent {
                                        tailf:info "% of total bandwidth";
                                        description "% of total bandwidth";
                                        type uint16 {
                                            range "1..100";
                                            tailf:info "<1-100>;;percentage";
                                        }
                                    }
                                }
                                leaf burst {
                                    tailf:cli-drop-node-name;
                                    type uint32 {
                                        tailf:info "<32-64000000>;;Burst in bytes";
                                        range "32..64000000";
                                    }
                                }
                            }
                        }
                        case queue-buffers-case {
                            // policy-map * / class * / queue-buffers
                            container queue-buffers {
                                tailf:cli-drop-node-name;
                                when "../action-type = 'queue-buffers'";
                                leaf ratio {
                                    tailf:info "Relative buffer size for queue";
                                    description "Relative buffer size for queue";
                                    type uint8 {
                                        tailf:info "<0-100>;;Queue-buffers ratio limit";
                                        range "0..100";
                                    }
                                }
                            }
                        }
        	            case queue-limit-case {
                            // policy-map * / class * / queue-limit
                            container queue-limit {
                                //tailf:info "Queue Max Threshold for Tail Drop";
                                tailf:cli-compact-syntax;
                                tailf:cli-sequence-commands {
                                    tailf:cli-reset-siblings;
                                }
                                tailf:cli-drop-node-name;
                                when "../action-type = 'queue-limit'";
                                leaf queue-limit-value {
                                    tailf:cli-drop-node-name;
                                    type uint32 {
                                        tailf:info "<1-8192000>  in bytes, <1-3400> in ms, "+
                                            "<1-32768> in packets by default";
                                        range "1..8192000";
                                    }
                                }
                                leaf queue-limit-type {
                                tailf:cli-drop-node-name;
                                type enumeration {
                                    enum bytes {
                                    tailf:info "in bytes";
                                }
                                enum ms {
                                    tailf:info "in milliseconds";
                                }
                                enum packets {
                                    tailf:info "in packets";
                                }
                                enum us {
                                    tailf:info "in microseconds";
                                }
                            }
                        }
                    }
                    container queue-limit-dscp {
                        //tailf:info "Queue Max Threshold for Tail Drop";
                        tailf:cli-compact-syntax;
                        tailf:cli-drop-node-name;
                        when "../action-type = 'queue-limit'";
                        leaf dscp {
                            tailf:info "parameters for each dscp value";
                            description "parameters for each dscp value";
                            type empty;
                        }
                        leaf values {
                            tailf:info "dscp values";
                            description "dscp values";
                            type empty;
                        }
                        leaf-list sdcp-val {
                            tailf:cli-drop-node-name;
                            type dscp-type;
                        }
                        leaf percent {
                            tailf:info "% of threshold";
                            description "% of threshold";
                            type uint8 {
                                tailf:info "<0-100>;;% of threshold";
                                range "0..100";
                            }
                        }
                    }
        	    }
        	    case random-detect {
                    // policy-map * / class * / random-detect
                    container random-detect {
                        //tailf:info "Enable Random Early Detection as drop policy";
                        //presence true;
                        tailf:cli-drop-node-name;
                        when "../action-type = 'random-detect'";
                        container aggregate {
                            tailf:info "aggregate subclasses";
                            description "aggregate subclasses";
                            tailf:cli-compact-syntax;
                            tailf:cli-sequence-commands {
                                tailf:cli-reset-siblings;
                            }
                            presence true;
                            leaf minimum-thresh {
                                tailf:info "minimum threshold for red aggregate";
                                description "minimum threshold for red aggregate";
                                type uint32 {
                                    tailf:info "<0-1000000>;;minimum threshold (number of packets)";
                                    range "0..1000000";
                                }
                            }
                            leaf maximum-thresh {
                                tailf:info "maximum threshold for red aggregate";
                                description "maximum threshold for red aggregate";
                                type uint32 {
                                    tailf:info "<0-1000000>;;maximum threshold (number of packets)";
                                    range "0..1000000";
                                }
                            }
                            leaf mark-probability {
                                tailf:info "mark-probability for red aggregate";
                                description "mark-probability for red aggregate";
                                type empty;
                            }
                            leaf denominator {
                                tailf:cli-drop-node-name;
                                type uint32 {
                                    tailf:info "<0-65535>;;mark probability denominator";
                                    range "0..65535";
                                }
                            }
                        }
                        container discard-class {
                            tailf:info "parameters for each discard-class value";
                            description "parameters for each discard-class value";
                            tailf:cli-compact-syntax;
                            tailf:cli-sequence-commands;
                            leaf dclass {
                                tailf:cli-drop-node-name;
                                tailf:cli-incomplete-command;
                                type uint16 {
                                    range "0..7";
                                    tailf:info "<0-7>;;discard-class value";
                                }
                            }
                            uses random-detect-grouping;
                        }
                        leaf discard-class-based {
                            tailf:info "Enable discard-class-based WRED as drop policy";
                            description "Enable discard-class-based WRED as drop policy";
                            tailf:cli-full-command;
                            type empty;
                        }
                        leaf dscp-based {
                            tailf:info "Enable dscp-based WRED as drop policy";
                            description "Enable dscp-based WRED as drop policy";
                            tailf:cli-full-command;
                            type empty;
                        }
                        list dscp {
                            tailf:info "parameters for each dscp value";
                            description "parameters for each dscp value";
        		            tailf:cli-suppress-mode;
                            tailf:cli-compact-syntax;
                            tailf:cli-sequence-commands;
        		            key dscp-val;
                            leaf dscp-val {
                                type dscp-type;
                            }
                            uses random-detect-grouping;
                        }
                        leaf ecn {
                            tailf:info "explicit congestion notification";
                            description "explicit congestion notification";
                            tailf:cli-full-command;
                            type empty;
                        }
                        leaf exponential-weighting-constant {
                            tailf:info "weight for mean queue depth calculation";
                            description "weight for mean queue depth calculation";
                            tailf:cli-full-command;
                            type uint16 {
                                range "1..16";
                                tailf:info "<1-16>;;integer in 1..16 used in weighted "+
                                    "average to mean 2^number";
                            }
                        }
                        leaf prec-based {
                            tailf:info "Enable precedence-based WRED as drop policy";
                            description "Enable precedence-based WRED as drop policy";
                            tailf:cli-full-command;
                            type empty;
                        }
                        container precedence {
                            tailf:info "parameters for each precedence value";
                            description "parameters for each precedence value";
                            tailf:cli-sequence-commands;
                            tailf:cli-compact-syntax;
                            leaf prec {
                                tailf:cli-drop-node-name;
                                tailf:cli-incomplete-command;
                                type precedence-type2;
                            }
                            uses random-detect-grouping;
                        }
                    }
        	    }
        	    case service-policy-case {
                      // policy-map * / class * / service-policy
                      leaf service-policy {
                        //tailf:info "Configure Flow Next";
                        tailf:cli-full-command;
                        tailf:cli-drop-node-name;
                        when "../action-type = 'service-policy'";
                        type string;
                        tailf:non-strict-leafref {
                            path "/ios:native/policy-map/name";
                        }
                    }
        	    }
        	    case set-case {
                    // policy-map * / class * / set
                    container set {
                        //tailf:info "Set QoS values";
                        tailf:cli-drop-node-name;
                        when "../action-type = 'set'";
                        // policy-map * / class * / set atm-clp
                        leaf atm-clp {
                            tailf:info "Set ATM CLP bit to 1";
                            description "Set ATM CLP bit to 1";
                            tailf:cli-full-command;
                            type empty;
                        }
                        // policy-map * / class * / set cos
                        container cos {
                        tailf:info "Set IEEE 802.1Q/ISL class of service/user "+
                            "priority";
                        description "Set IEEE 802.1Q/ISL class of service/user "+
                            "priority";
                        tailf:cli-compact-syntax;
                        tailf:cli-sequence-commands;
                        choice cos-type {
                            case a {
                                leaf val {
                                    tailf:cli-drop-node-name;
                                    type uint16 {
                                        range "0..7";
                                        tailf:info "<0-7>;;cos value";
                                    }
                                }
                            }
                            case b {
                                leaf pack {
                                    tailf:cli-drop-node-name;
                                    type enumeration {
                                        enum dscp {
                                            tailf:code-name "pack_dscp";
                                            tailf:info "Set value from packet dscp";
                                        }
                                        enum precedence {
                                            tailf:code-name "pack_precedence";
                                            tailf:info "Set value from packet "+
                                                "precedence.";
                                            }
                                        }
                                    }
                                    leaf table {
                                        tailf:info "Set codepoint value based on tablemap.";
                                        description "Set codepoint value based on tablemap.";
                                        type string {
                                            tailf:info "WORD;;table-map name";
                                        }
                                        tailf:non-strict-leafref {
                                        path "/ios:native/table-map/name";
                                    }
                                }
                            }
                        }
                    }
                    // policy-map * / class * / set discard-class
                    leaf discard-class {
                        tailf:info "Discard behavior identifier";
                        description "Discard behavior identifier";
                        tailf:cli-full-command;
                        type uint16 {
                            range "0..7";
                            tailf:info "<0-7>;;Discard Class value";
                        }
                    }
                    // policy-map * / class * / set dscp
                    container dscp {
                        tailf:info "Set DSCP in IP(v4) and IPv6 packets";
                        description "Set DSCP in IP(v4) and IPv6 packets";
                        tailf:cli-compact-syntax;
                        leaf tunnel {
                            tailf:info "set tunnel packet dscp";
                            description "set tunnel packet dscp";
                            type empty;
                        }
                        leaf dscp-val {
                        tailf:cli-drop-node-name;
                        type dscp-type;
                    }
                }
                // policy-map * / class * / set fr-de
                leaf fr-de {
                    tailf:info "Set FR DE bit to 1";
                    description "Set FR DE bit to 1";
                    tailf:cli-full-command;
                    type empty;
                }
                // policy-map * / class * / set ip
                container ip {
                    tailf:info "Set IP specific values";
                    description "Set IP specific values";
                    choice ip-choice {
                        container dscp {
                            tailf:info "Set IP DSCP (DiffServ CodePointint)";
                            description "Set IP DSCP (DiffServ CodePointint)";
                            tailf:cli-compact-syntax;
                            leaf tunnel {
                                tailf:info "set tunnel packet dscp";
                                description "set tunnel packet dscp";
                                type empty;
                            }
                            leaf dscp-val {
                                tailf:cli-drop-node-name;
                                type dscp-type;
                            }
                        }
                        container precedence {
                            tailf:info "Set IP precedence";
                            description "Set IP precedence";
                            presence "Set IP precedence";
                            leaf precedence-val {
                                tailf:cli-drop-node-name;
                                type precedence-type;
                            }
                        }
                    }
                }
                // policy-map * / class * / set mpls
                container mpls {
                    tailf:info "Set MPLS specific values";
                    description "Set MPLS specific values";
                    container experimental {
                        tailf:info "Set Experimental value";
                        description "Set Experimental value";
                        // 0-7
                        container imposition {
                            tailf:info "Set Experimental value at tag imposition";
                            description "Set Experimental value at tag imposition";
                            leaf exp-value {
                                tailf:cli-drop-node-name;
                                tailf:cli-full-command;
                                type uint8 {
                                    tailf:info "<0-7>;;Experimental value";
                                    range "0..7";
                                }
                            }
                            // dscp
                            // precedence
                        }
                        // topmost
                        container topmost {
                            tailf:info "Set Experimental value  on topmost label";
                            description "Set Experimental value  on topmost label";
                            leaf exp-value {
                                tailf:cli-drop-node-name;
                                tailf:cli-full-command;
                                    type uint8 {
                                        tailf:info "<0-7>;;Experimental value";
                                        range "0..7";
                                    }
                                }
                            }
                        }
                    }
                    // policy-map * / class * / set qos-group
                    container qos-group {
                        tailf:info "Set QoS Group";
                        description "Set QoS Group";
                        leaf qos-group-value {
                            tailf:cli-drop-node-name;
                            tailf:cli-full-command;
                            type uint8 {
                                range "0..99";
                            }
                        }
                        // dscp
                        // mpls
                        // precedence
                    }
                }
        	}
        	case shape-case {
                // policy-map * / class * / shape
                container shape {
                    //tailf:info "Traffic Shaping";
                    tailf:cli-drop-node-name;
                    when "../action-type = 'shape'";
                    // policy-map * / class * / shape adaptive
                    leaf adaptive {
                        tailf:info "Enable Traffic Shaping adaptation to BECN";
                        description "Enable Traffic Shaping adaptation to BECN";
                        tailf:cli-full-command;
                        type uint32 {
                            range "8000..154400000";
                            tailf:info "<8000-154400000>;;Lower Bound Target Bit "+
                               "Rate (bits per second)";
                        }
                    }
                    // policy-map * / class * / shape average
                    container average {
                    tailf:info "configure token bucket: CIR (bps) [Bc (bits) "+
                        "[Be (bits)]], send out Bc only per interval";
                    description "configure token bucket: CIR (bps) [Bc (bits) "+
                        "[Be (bits)]], send out Bc only per interval";
                    tailf:cli-sequence-commands;
                    tailf:cli-compact-syntax;
                    choice average-choice {
                        case a {
                            leaf bit-rate {
                                tailf:cli-drop-node-name;
                                type uint64 {
                                    //range "8000..154400000";
                                    //FIXME: what is range max?
                                    tailf:info "<8000-max>;;Target Bit "+
                                        "Rate (bits per second), the value "+
                                        "needs to be a multiple of 8000";
                                }
                            }
                            leaf bits-per-interval-sustained {
                                tailf:cli-drop-node-name;
                                type uint32 {
                                    range "256..154400000";
                                    tailf:info "<256-154400000>;;bits per "+
                                        "interval, sustained. Needs to be "+
                                        "multiple of 128. Recommend not to "+
                                        "configure it, the algorithm will "+
                                        "find out the best value";
                                }
                            }
                            leaf bits-per-interval-excess {
                                tailf:cli-drop-node-name;
                                type uint32 {
                                    range "0..154400000";
                                    tailf:info "<0-154400000>;;bits per "+
                                        "interval, excess. Needs to be "+
                                        "multiple of 128. Bc will be used if "+
                                        "you don't configure it.";
                                    }
                                }
                            }
                            case b {
                                leaf percent {
                                    tailf:info "% of interface bandwidth for "+
                                        "Committed information rate";
                                    description "% of interface bandwidth for "+
                                        "Committed information rate";
                                    type percentage-type;
                                }
                                leaf burst-size-sustained {
                                    tailf:cli-incomplete-command;
                                    tailf:cli-drop-node-name;
                                    type uint16 {
                                        range "10..2000";
                                        tailf:info "<10-2000>;;Sustained burst "+
                                            "size in msec";
                                        }
                                    }
                                    leaf ms {
                                        tailf:info "milliseconds";
                                        description "milliseconds";
                                        type empty;
                                    }
                                    container bse {
                                        tailf:cli-drop-node-name;
                                        tailf:cli-flatten-container;
                                        tailf:cli-sequence-commands;
                                        tailf:cli-compact-syntax;
                                        leaf burst-size-excess {
                                            tailf:cli-incomplete-command;
                                            type uint16 {
                                                range "10..2000";
                                                tailf:info "<10-2000>;;Excess burst "+
                                                    "size in msec";
                                            }
                                        }
                                        leaf ms {
                                            tailf:info "milliseconds";
                                            description "milliseconds";
                                            type empty;
                                        }
                                    }
                                }
                            }
                        }
                        // policy-map * / class * / shape fecn-adapt
                        leaf fecn-adapt {
                            tailf:info "Enable Traffic Shaping reflection of FECN as "+
                                "BECN";
                            description "Enable Traffic Shaping reflection of FECN as "+
                                "BECN";
                            tailf:cli-full-command;
                            type empty;
                        }
                        // policy-map * / class * / shape fr-voice-adapt
                        container fr-voice-adapt {
                            tailf:info "Enable rate adjustment depending on voice "+
                                  "presence";
                            description "Enable rate adjustment depending on voice "+
                                "presence";
                            presence "Enable rate adjustment depending on voice "+
                                "presence" ;
                            leaf deactivation {
                                type uint16 {
                                    range "1..10000";
                                    tailf:info "<1-10000>;;de-activation delay in "+
                                        "seconds";
                                    }
                                }
                            }
                            // policy-map * / class * / shape max-buffers
                            leaf max-buffers {
                                tailf:cli-full-command;
                                tailf:info "Set Maximum Buffer Limit";
                                description "Set Maximum Buffer Limit";
                                type uint16 {
                                    range "1..4096";
                                    tailf:info "<1-4096>;;Maximum Buffer Limit";
                                }
                            }
                        }
        	        }
        	        case trust-case {
                        // policy-map * / class * / trust
                        leaf trust {
                            //tailf:info "Set trust value for the class";
                            tailf:cli-drop-node-name;
                            when "../action-type = 'trust'";
                                type enumeration {
                                    enum cos {
                                        tailf:info "trust value for the class";
                                    }
                                    enum dscp {
                                        tailf:info "trust value for the class";
                                    }
                                    enum ip-precedence {
                                        tailf:info "trust value for the class";
                                    }
                                }
                            }
                        }
                    }
                }
            }
            // policy-map * / description
            leaf "description" {
                tailf:info "Policy-Map description";
                description "Policy-Map description";
                tailf:cli-multi-value;
                type string {
                    length "1..200";
                    tailf:info "LINE;;Description of this policy-map (up to "
                    +"200 characters)";
                }
            }
            // policy-map * /sequence-interval
            leaf sequence-interval {
                tailf:info "Enable sequence number capability";
                description "Enable sequence number capability";
                when "../type = 'appnav'";
                type uint16 {
                    tailf:info "<0-65535>;;Sequence Number Interval";
                }
            }
        }

/// ========================================================================
/// service-chain
/// ========================================================================

        grouping config-service-chain-grouping {
            leaf description {
                tailf:info "Service function forwarder description";
                description "Service function forwarder description";
                tailf:cli-multi-value;
                type string {
                    tailf:info "LINE;;Up to 256 characters describing this " + "service function forwarder";
                    length "1..256";
                }
            }
            container ip {
                tailf:info "IP address for Service Function Forwarder";
                description "IP address for Service Function Forwarder";
                leaf address {
                    tailf:info "Set IPv4 address";
                    description "Set IPv4 address";
                    type inet:ipv4-address {
                        tailf:info "A.B.C.D;;IP address of Service Function Forwarder";
                    }
                }
            }
        }

        container service-chain {
            tailf:info "Service Chain mode";
            description "Service Chain mode";
            list service-function {
                tailf:info "Service function details";
                description "Service function details";
                tailf:cli-mode-name "config-service-chain-sf";
                key "name";
                leaf name {
                    tailf:info "WORD;;Service function name";
                    description "WORD;;Service function name";
                    type string;
                }
                container config-service-chain-sf-mode {
                    tailf:cli-drop-node-name;
                    leaf description {
                        tailf:info "Service function description";
                        description "Service function description";
                        tailf:cli-multi-value;
                        tailf:cli-full-command;
                        type string {
                            tailf:info "LINE;;Up to 256 characters describing this "
                             +"service function";
                            length "1..256";
                        }
                    }
                    container encapsulation {
                        tailf:info "Service node encapsulation";
                        description "Service node encapsulation";
                        container gre {
                            tailf:info "Service node encapsulation type";
                            description "Service node encapsulation type";
                            leaf enhanced {
                                tailf:info "Add enhanced NSH TLV information";
                                description "Add enhanced NSH TLV information";
                                type enumeration {
                                    enum copy {
                                        tailf:info "Send a copy of the packet";
                                    }
                                    enum divert {
                                        tailf:info "Divert the packet (default)";
                                    }
                                }
                            }
                        }
                        leaf none {
                            tailf:info "Service node encapsulation type";
                            description "Service node encapsulation type";
                            type empty;
                        }
                    }
                    container ip {
                        tailf:info "Service node";
                        description "Service node";
                        leaf address {
                            type inet:ipv4-address {
                                tailf:info "A.B.C.D;;Service node";
                            }
                        }
                    }
                }
            }
            container service-function-forwarder {
                tailf:info "Service function forwarder details";
                description "Service function forwarder details";
                list service-ff-name {
                    tailf:cli-drop-node-name;
                    tailf:cli-mode-name "config-service-chain-sff";
                    key "name";
                    leaf name {
                        tailf:info "WORD;;Service function forwarder name";
                        description "WORD;;Service function forwarder name";
                        type string;
                    }
                    uses config-service-chain-grouping;
                }
                container local {
                    tailf:info "Local service function forwarder";
                    description "Local service function forwarder";
                    tailf:cli-add-mode;
                    tailf:cli-mode-name "config-service-chain-sff";
                    presence true;
                    uses config-service-chain-grouping;
                }
            }
            list service-path {
                tailf:info "Service Path Entries";
                description "Service Path Entries";
                tailf:cli-mode-name "config-service-chain-path";
                key "service-path-id";
                leaf service-path-id {
                    type uint32 {
                        range "0..16777215";
                        tailf:info "<0-16777215>;;Service Path ID";
                    }
                }
                container config-service-chain-path-mode {
                    tailf:cli-drop-node-name;
                    leaf description {
                        tailf:info "Path Description";
                        description "Path Description";
                        tailf:cli-multi-value;
                        tailf:cli-full-command;
                        type string {
                            tailf:info "LINE;;Up to 256 characters describing this "
                                +"service path";
                            length "1..256";
                        }
                    }
                    container service-index {
                        tailf:info "Service Index";
                        description "Service Index";
                        list services {
                            tailf:cli-drop-node-name;
                            tailf:cli-suppress-mode;
                            key "service-index-id";
                            leaf service-index-id {
                                type uint8 {
                                range "2..255";
                                tailf:info "<2-255>;;Service Index ID";
                            }
                        }
                        choice service-type-choice {
                            leaf service-function {
                                tailf:info "Service Function name";
                                description "Service Function name";
                                type string {
                                    tailf:info "WORD;;Service Function name";
                                }
                            }
                            leaf service-function-forwarder {
                                tailf:info "Service Function Forwarder name";
                                description "Service Function Forwarder name";
                                type string {
                                    tailf:info "WORD;;Service Function Forwarder name";
                                }
                            }
                            leaf terminate {
                                tailf:info "Terminate(Proxy)";
                                description "Terminate(Proxy)";
                                type empty;
                                }
                            }
                        }
                    }
                }
            }
        }
    }

/// ========================================================================
/// eof
/// ========================================================================

}
