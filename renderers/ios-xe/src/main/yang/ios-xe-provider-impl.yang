/*
 * Copyright (c) 2016 Cisco Systems, Inc. and others.  All rights reserved.
 *
 * This program and the accompanying materials are made available under the
 * terms of the Eclipse Public License v1.0 which accompanies this distribution,
 * and is available at http://www.eclipse.org/legal/epl-v10.html
 */

module ios-xe-provider-impl {
    yang-version 1;
    namespace "urn:opendaylight:params:xml:ns:yang:groupbasedpolicy:renderer:ios-xe-provider:impl:config";
    prefix "ios-xe-provider-impl";

    import config { prefix config; revision-date 2013-04-05; }
    import opendaylight-md-sal-binding { prefix mdsal; revision-date 2013-10-28; }
    import groupbasedpolicy-cfg { prefix gbpcfg; revision-date 2015-11-06; }
    import renderer { prefix gbprenderer; revision-date 2015-11-03; }

    description
        "This module contains the base YANG definitions for
          ios-xe-provider impl implementation.";

    revision "2016-05-17" {
        description
            "Initial revision.";
    }

    identity ios-xe-provider-impl {
        base "config:module-type";
        config:java-name-prefix IosXeProvider;
    }

    // Augments the 'configuration' choice node under modules/module.
    augment "/config:modules/config:module/config:configuration" {
        case ios-xe-provider-impl {
            when "/config:modules/config:module/config:type = 'ios-xe-provider-impl'";
        }
    }
}
