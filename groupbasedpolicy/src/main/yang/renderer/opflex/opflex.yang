/*
 * Copyright (c) 2014 Cisco Systems, Inc. and others.  All rights reserved.
 *
 * This program and the accompanying materials are made available under the
 * terms of the Eclipse Public License v1.0 which accompanies this distribution,
 * and is available at http://www.eclipse.org/legal/epl-v10.html
 */

module opflex {
    yang-version 1;

    namespace "urn:opendaylight:groupbasedpolicy:opflex";
    prefix "opflex";

    import ietf-inet-types { prefix "inet"; revision-date 2010-09-24; }

    import yang-ext {prefix ext; revision-date "2013-07-09";}
    import gbp-common {prefix gbp-common;}
    import endpoint {prefix endpoint;}

    description
        "This module defines the group-based policy OpFlex renderer model.";

    revision "2014-05-28" {
        description
            "Initial revision.";
    }
    
    typedef serialization {
        description
            "The serialization to use for OpFlex messages.";

        type enumeration {
            enum json {
                description
                "JSON 1.0 serialization.";
            }
            enum xml {
                description
                "XML serialization.";
            }
            enum binary {
                description
                "OpFlex binary serialization.";
            }
        }
    }

    container discovery-definitions {
        description
            "The nodes that any OpFlex agent needs to communicate
             with in an OpFlex policy fabric.";

        config true;

        leaf domain {
            description
                "The OpFlex administrative domain.";
    
            config true;
    
            type string;
        }

        list policy-repository {
            description
                "A repository that the OpFlex agent can use for resolving
                 policies.";

            key "id";

            leaf id {
                description 
                   "The id for the policy repository.";
                type string;
            }
            leaf port {
                description 
                   "The port number to use for the connection";
                type int32;
            }
            leaf serialization-type {
                description 
                    "The serialization to use for this connection.";
                type serialization;
            }
        }

        list endpoint-registry {
            description
                "A repository that the OpFlex agent can use for registration
                 and lookup of endpoints.";

            key "id";

            leaf id {
                description 
                   "The id for the endpoint registry.";
                type string;
            }
            leaf port {
                description 
                   "The port number to use for the connection";
                type int32;
            }
            leaf serialization-type {
                description 
                    "The serialization to use for this connection.";
                type serialization;
            }
        }

        list observer {
            description
                "A repository that the OpFlex agent can send State Report
                 messages to.";

            key "id";

            leaf id {
                description 
                   "The id for the Observer.";
                type string;
            }
            leaf port {
                description 
                   "The port number to use for the connection";
                type int32;
            }
            leaf serialization-type {
                description 
                    "The serialization to use for this connection.";
                type serialization;
            }
        }
    }

    grouping endpoint-location {
        description 
            "The location for this endpoint in the overlay network";

        leaf location-type {
            default internal;

            type enumeration {
                enum internal {
                    description 
                    "The endpoint is located on a port that is part of 
                     the overlay network.  You must include the node
                     ID and port number for this endpoint.";
                }
                enum external {
                    description "This endpoint is not inside the overlay.";
                }
            }
        }
        leaf agent-id {
            description 
                "The OpFlex agent where the endpoing is located. Must be included 
                 for all internal endpoints.  The format is the agent identifier,
                 which is an IP address or DNS name ':' port number.";
            type string;
        }
        leaf agent-ep-location {
            description 
                "The location of the endpoint on the OpFlex agent. The format of
                 this is dependent on the renderer used by the agent.";
            type string;
        }
    }

    augment "/endpoint:endpoints/endpoint:endpoint" {
        ext:augment-identifier "opflex-overlay-context";
        uses endpoint-location;
    }

    augment "/endpoint:register-endpoint/endpoint:input" {
        ext:augment-identifier "opflex-overlay-context-input";
        uses endpoint-location;
    }

    augment "/endpoint:endpoints/endpoint:endpoint-l3" {
        ext:augment-identifier "opflex-overlay-context-l3";
        uses endpoint-location;
    }

}
