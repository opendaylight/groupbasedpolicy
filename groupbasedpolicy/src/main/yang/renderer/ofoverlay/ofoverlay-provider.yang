module ofoverlay-provider {
     yang-version 1;
     namespace "urn:opendaylight:params:xml:ns:yang:controller:config:ofoverlay-provider";
     prefix "ofoverlay-provider";

     import config { prefix config; revision-date 2013-04-05; }

     description
         "This module contains the base YANG definitions for 
          ofoverlay-provider services.";

     revision "2014-04-21" {
         description
             "Initial revision.";
     }

     identity ofoverlay-provider {
         base "config:service-type";
         config:java-class "org.opendaylight.yang.gen.v1.urn.opendaylight.groupbasedpolicy.ofoverlay.rev140528.OfoverlayData";
     }
}
