module ofoverlay-provider-impl {
    yang-version 1;
    namespace "urn:opendaylight:params:xml:ns:yang:controller:config:ofoverlay-provider:impl";
    prefix "ofoverlay-provider-impl";

    import config { prefix config; revision-date 2013-04-05; }
    import opendaylight-md-sal-binding { prefix mdsal; revision-date 2013-10-28; }

    description
        "This module contains the base YANG definitions for 
          ofoverlay-provider impl implementation.";

    revision "2014-06-11" {
        description
            "Initial revision.";
    }

    identity ofoverlay-provider-impl {
        base "config:module-type";

        config:java-name-prefix OFOverlayProvider;
    }

    // Augments the 'configuration' choice node under modules/module.  
    augment "/config:modules/config:module/config:configuration" {
        case ofoverlay-provider-impl {
            when "/config:modules/config:module/config:type = 'ofoverlay-provider-impl'";

            //wires in the data-broker service 
            container data-broker {
                uses config:service-ref {
                    refine type {
                        mandatory true;
                        config:required-identity mdsal:binding-async-data-broker;
                    }
                }
            }
            // RPC Registry
            container rpc-registry {
                uses config:service-ref {
                    refine type {
                        mandatory true;
                        config:required-identity mdsal:binding-rpc-registry;
                    }
                }
            }
        }
    }
}
