/*
 * Copyright (c) 2015 Cisco Systems, Inc. and others.  All rights reserved.
 *
 * This program and the accompanying materials are made available under the
 * terms of the Eclipse Public License v1.0 which accompanies this distribution,
 * and is available at http://www.eclipse.org/legal/epl-v10.html
 */

module groupbasedpolicy-cfg {
    yang-version 1;
    namespace "urn:opendaylight:params:xml:ns:yang:controller:config:groupbasedpolicy";
    prefix "gbpcfg";

    import config { prefix config; revision-date 2013-04-05; }
    import opendaylight-md-sal-binding { prefix mdsal; revision-date 2013-10-28; }

    description
        "This module contains the base YANG definitions for
          groupbasedpolicy impl implementation.";

    revision "2015-11-06" {
        description
            "Initial revision.";
    }

    identity ep-renderer-augmentation-registry {
        status deprecated;
        description
            "ep-renderer-augmentation-registry service definition";

        base "config:service-type";
        config:java-class "org.opendaylight.groupbasedpolicy.api.EpRendererAugmentationRegistry";
        config:disable-osgi-service-registration;
    }

    identity domain-specific-registry {
        status deprecated;
        description
            "domain-specific-registry service definition";

        base "config:service-type";
        config:java-class "org.opendaylight.groupbasedpolicy.api.DomainSpecificRegistry";
        config:disable-osgi-service-registration;
    }

    identity policy-validator-registry {
        status deprecated;
        description
            "policy-validator-registry service definition";

        base "config:service-type";
        config:java-class "org.opendaylight.groupbasedpolicy.api.PolicyValidatorRegistry";
        config:disable-osgi-service-registration;
    }

    identity statistics-manager {
        status deprecated;
        description
            "statistics-manager service definition";

        base "config:service-type";
        config:java-class "org.opendaylight.groupbasedpolicy.api.StatisticsManager";
        config:disable-osgi-service-registration;
    }

    identity policy-validator-registry-impl {
        base "config:module-type";

        config:provided-service policy-validator-registry;
        config:java-name-prefix PolicyValidatorRegistry;
    }

    identity ep-renderer-augmentation-registry-impl {
        base "config:module-type";

        config:provided-service ep-renderer-augmentation-registry;
        config:java-name-prefix EpRendererAugmentationRegistryImpl;
    }

    identity domain-specific-registry-impl {
        base "config:module-type";

        config:provided-service domain-specific-registry;
        config:java-name-prefix DomainSpecificRegistry;
    }

    identity statistics-manager-impl {
        base "config:module-type";

        config:provided-service statistics-manager;
        config:java-name-prefix StatisticsManagerImpl;
    }

    identity groupbasedpolicy-impl {
        base "config:module-type";

        config:java-name-prefix Groupbasedpolicy;
    }

    // Augments the 'configuration' choice node under modules/module.
    augment "/config:modules/config:module/config:configuration" {
        case groupbasedpolicy-impl {
            when "/config:modules/config:module/config:type = 'groupbasedpolicy-impl'";
        }
        case policy-validator-registry-impl {
            when "/config:modules/config:module/config:type = 'policy-validator-registry-impl'";
        }
        case ep-renderer-augmentation-registry-impl {
            when "/config:modules/config:module/config:type = 'ep-renderer-augmentation-registry-impl'";
        }
        case domain-specific-registry-impl {
            when "/config:modules/config:module/config:type = 'domain-specific-registry-impl'";
        }
        case statistics-manager-impl {
            when "/config:modules/config:module/config:type = 'statistics-manager-impl'";
        }
    }
}
