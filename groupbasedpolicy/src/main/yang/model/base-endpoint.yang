/*
 * Copyright (c) 2016 Cisco Systems, Inc. and others.  All rights reserved.
 *
 * This program and the accompanying materials are made available under the
 * terms of the Eclipse Public License v1.0 which accompanies this distribution,
 * and is available at http://www.eclipse.org/legal/epl-v10.html
 */

module base-endpoint {
    yang-version 1;

    namespace "urn:opendaylight:groupbasedpolicy:base_endpoint";
    prefix "base-endpoint";

    import gbp-common { prefix gbp-common; revision-date 2014-04-21; }
    import forwarding { prefix forwarding; revision-date 2016-04-27; }
    import ietf-inet-types { prefix inet; revision-date 2013-07-15; }
    import yang-ext { prefix ext; revision-date "2013-07-09"; }

    revision "2016-04-27" {
        description
                "Initial revision.";
    }

    grouping address-endpoint-key {
        uses forwarding:context-key;
        uses forwarding:has-address-type;
        leaf address {
            type string;
            mandatory true;
        }
    }

    grouping has-child-endpoints {
        list child-endpoint {
            key "context-type context-id address-type address";
            uses address-endpoint-key;
        }
    }

    grouping parent-child-endpoints {
        choice parent-endpoint-choice {
            case parent-containment-endpoint-case {
                list parent-containment-endpoint {
                    key "context-type context-id";
                    uses forwarding:context-key;
                }
            }
            case parent-endpoint-case {
                list parent-endpoint {
                    key "context-type context-id address-type address";
                    uses address-endpoint-key;
                }
            }
        }
        uses has-child-endpoints;
    }

    grouping common-endpoint-fields {
        leaf tenant {
            type gbp-common:tenant-id;
            mandatory true;
            description
                        "The tenant with which this endpoint is associated";
        }
        container network-containment {
            choice containment {
                description
                            "The network domain associated with this endpoint's fowarding
                            context.";
                case network-domain-containment {
                    uses forwarding:network-domain-key;
                }
                case forwarding-context-containment {
                    uses forwarding:context-key;
                }
            }
        }
        leaf-list endpoint-group {
            type gbp-common:endpoint-group-id;
            description
                        "The groups associated with this endpoint";
            ordered-by user;
            min-elements 1;
        }
        leaf-list condition {
            type gbp-common:condition-name;
            description
                        "The conditions associated with this endpoint";
        }
        leaf timestamp {
            type int64;
            description
                        "The last timestamp associated with this endpoint record. This
                        will be used for aging data in the registry.";
        }
    }

    grouping address-endpoint-fields {
        uses address-endpoint-key;
        uses parent-child-endpoints;
        uses common-endpoint-fields;
    }

    grouping containment-endpoint-fields {
        uses forwarding:context-key;
        uses has-child-endpoints;
        uses common-endpoint-fields;
    }

    grouping has-endpoint-group-conditions {
        description
                "Base type for object with endpoint group to condition mappings.";

        leaf endpoint-group {
            description "The endpoint group conditions to assign";
            type gbp-common:endpoint-group-id;
        }
        list endpoint-group-condition {
            description
                        "The conditions associated with this endpoint group";
            key "condition";
            leaf condition {
                description "A condition name to associate.";
                type gbp-common:condition-name;
            }
        }
    }

    grouping internal-location-fields {
        description "Location inside ODL - node and node-connector
            are represented directly in ODL.";
        leaf internal-node {
            mandatory true;
            type instance-identifier;
        }
        leaf internal-node-connector {
            type instance-identifier;
        }
    }

    grouping external-location-fields {
        description "Location outside of ODL - node and node-connector
            are outside of ODL. external-node-mount-point is path
            to external system where node and node-connector are located.";
        leaf external-node-mount-point {
            mandatory true;
            type instance-identifier;
        }
        leaf external-node {
            type string; // TODO switch to external-reference
        }
        leaf external-node-connector {
            type string; // TODO switch to external-reference
        }
    }

    grouping has-absolute-location {
        container absolute-location {
            choice location-type {
                case internal-location-case {
                    uses internal-location-fields;
                }
                case external-location-case {
                    uses external-location-fields;
                }
            }
        }
    }

    grouping has-relative-location {
        container relative-locations {
            list internal-location {
                key "internal-node internal-node-connector";
                uses internal-location-fields;
            }
            list external-location {
                key "external-node-mount-point external-node-connector";
                uses external-location-fields;
            }
        }
    }

    grouping has-location {
        uses has-absolute-location;
        uses has-relative-location;
    }

    grouping nat-fields {
        description "Support for IP NAT";
        leaf nat-address {
            description "Ip address the L3Endpoint translates to.";
            type inet:ip-address;
        }
    }

    container endpoints {
        description
                "Repository for operational state data about endpoints needed
                for policy resolution.";
        config false;

        container address-endpoints {
            list address-endpoint {
                key "context-type context-id address-type address";
                uses address-endpoint-fields;
            }
        }

        container containment-endpoints {
            list containment-endpoint {
                key "context-type context-id";
                uses containment-endpoint-fields;
            }
        }
    }

    container endpoint-locations {
        config false;

        list address-endpoint-location {
            key "context-type context-id address-type address";
            uses address-endpoint-key;
            uses has-location;
        }

        list containment-endpoint-location {
            key "context-type context-id";
            uses forwarding:context-key;
            uses has-relative-location;
        }
    }

    rpc register-endpoint {
        description
                "Register a new endpoint into the registry. If there is already
                an existing endpoint with the same keys, they will be overwritten
                with the new information.";

        input {
            list address-endpoint-reg {
                key "context-type context-id address-type address";
                uses address-endpoint-fields;
                uses has-location;
            }
            list containment-endpoint-reg {
                key "context-type context-id";
                uses containment-endpoint-fields;
                uses has-relative-location;
            }
        }
    }

    rpc unregister-endpoint {
        description "Unregister an endpoint or endpoints from the registry.";

        input {
            list address-endpoint-unreg {
                key "context-type context-id address-type address";
                uses address-endpoint-key;
            }
            list containment-endpoint-unreg {
                key "context-type context-id";
                uses forwarding:context-key;
            }
        }
    }

    augment "/endpoints/address-endpoints/address-endpoint" {
        ext:augment-identifier "nat-address";
        uses nat-fields;
    }

    augment "/register-endpoint/input/address-endpoint-reg" {
        ext:augment-identifier "nat-address-input";
        uses nat-fields;
    }
}
