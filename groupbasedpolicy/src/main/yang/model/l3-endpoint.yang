/*
 * Copyright (c) 2014 Cisco Systems, Inc. and others.  All rights reserved.
 *
 * This program and the accompanying materials are made available under the
 * terms of the Eclipse Public License v1.0 which accompanies this distribution,
 * and is available at http://www.eclipse.org/legal/epl-v10.html
 */

module l3-endpoint {
    yang-version 1;

    namespace "urn:opendaylight:groupbasedpolicy:l3endpoint";
    prefix "gbp-l3-endpoint";

    import endpoint { prefix endpoint; revision-date 2014-04-21; }
    import ietf-inet-types {
        prefix inet;
        revision-date 2013-07-15;
    }
    import yang-ext {prefix ext; revision-date "2013-07-09";}

    revision "2015-12-17" {
        description
            "Initial revision.";
    }

    grouping nat-fields {
        description "Support for IP NAT";
        leaf nat-address {
            description "Ip address the L3Endpoint translates to.";
            type inet:ip-address;
        }
    }

    augment "/endpoint:endpoints/endpoint:endpoint-l3" {
        ext:augment-identifier "nat-address";
        uses nat-fields;
    }

    augment "/endpoint:register-endpoint/endpoint:input" {
        ext:augment-identifier "nat-address-input";
        uses nat-fields;
    }

}
