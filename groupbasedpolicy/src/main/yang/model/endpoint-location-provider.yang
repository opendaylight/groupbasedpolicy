/*
 * Copyright (c) 2015 Cisco Systems, Inc. and others.  All rights reserved.
 *
 * This program and the accompanying materials are made available under the
 * terms of the Eclipse Public License v1.0 which accompanies this distribution,
 * and is available at http://www.eclipse.org/legal/epl-v10.html
 */

module endpoint-location-provider {
    yang-version 1;

    namespace "urn:opendaylight:groupbasedpolicy:endpoint_location_provider";
    prefix "ep-loc-provider";

    import base-endpoint { prefix base-endpoint; revision-date 2016-04-27; }
    import forwarding { prefix forwarding; revision-date 2016-04-27; }

    description
        "This module defines network element structure for location provider.";

    revision "2016-04-19" {
        description
            "Initial revision.";
    }

    typedef provider-name {
        type string;
    }

    container location-providers {
        list location-provider {
            key "provider";
            leaf provider {
                type provider-name;
            }
            leaf priority {
                type uint32;
            }
            list provider-address-endpoint-location {
                key "context-type context-id address-type address";
                uses base-endpoint:address-endpoint-key;
                uses base-endpoint:has-location;
            }
            list provider-containment-endpoint-location {
                key "context-type context-id";
                uses forwarding:context-key;
                uses base-endpoint:has-relative-location;
            }
        }
    }
}
