/*
 * Copyright (c) 2015 Cisco Systems, Inc. and others.  All rights reserved.
 *
 * This program and the accompanying materials are made available under the
 * terms of the Eclipse Public License v1.0 which accompanies this distribution,
 * and is available at http://www.eclipse.org/legal/epl-v10.html
 */

module statistics {
    yang-version 1;

    namespace "urn:opendaylight:groupbasedpolicy:statistics";
    prefix "gbp-statistics";

    import endpoint {
        prefix endpoint;
        revision-date 2014-04-21;
    }
    import gbp-common {
        prefix gbp-common;
        revision-date 2014-04-21;
        }
    import ietf-inet-types {
        prefix inet;
        revision-date 2013-07-15;
    }
    import ietf-yang-types {
        prefix yang;
        revision-date 2013-07-15;
    }

    description
        "This module defines gbp statistics model.";

    revision "2015-12-15" {
        description
            "Initial revision.";
    }

    grouping statistic-records {
        container stat-records {
            //////////////////////
            //  EP combination  //
            //specific statistic//
            //////////////////////
            list ep-to-ep-statistic {
                key "src-mac-address src-l2c dst-mac-address dst-l2c";
                /////////////
                //Source EP//
                /////////////
                leaf src-mac-address {
                    type yang:mac-address;
                }
                leaf src-l2c {
                    type gbp-common:l2-bridge-domain-id;
                }
                leaf src-tenant {
                    type gbp-common:tenant-id;
                }
                leaf timestamp {
                    type uint64;
                    description
                        "Date and time of record creation in milliseconds
                        counting from 1.1.1970 00:00:00 UTC (= 0)";
                }
                //////////////////
                //Destination EP//
                //////////////////
                leaf dst-mac-address {
                    type yang:mac-address;
                }
                leaf dst-l2c {
                    type gbp-common:l2-bridge-domain-id;
                }
                leaf dst-tenant {
                    type gbp-common:tenant-id;
                }
                //////////////////////
                //  EPG combination //
                //specific statistic//
                //////////////////////
                list ep-epg-to-ep-epg-statistic {
                    key "src-epg dst-epg";
                    leaf src-epg {
                        type gbp-common:endpoint-group-id;
                    }
                    leaf dst-epg {
                        type gbp-common:endpoint-group-id;
                    }
                    list matched-rule-statistic {
                        key "contract subject matched-rule";
                        leaf contract {
                            type gbp-common:contract-id;
                        }
                        leaf subject {
                            type gbp-common:subject-name;
                        }
                        leaf matched-rule {
                            type gbp-common:rule-name;
                        }
                        leaf-list classifier {
                            type gbp-common:classifier-name;
                        }
                        leaf-list action {
                            type gbp-common:action-name;
                        }
                        leaf byte-count {
                            type int64;
                        }
                        leaf packet-count {
                            type int64;
                        }
                    }
                }
            }
        }
    }
}
