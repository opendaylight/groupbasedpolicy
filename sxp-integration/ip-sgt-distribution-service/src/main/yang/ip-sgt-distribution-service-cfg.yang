/*
 * Copyright (c) 2016 Cisco Systems, Inc. and others.  All rights reserved.
 *
 * This program and the accompanying materials are made available under the
 * terms of the Eclipse Public License v1.0 which accompanies this distribution,
 * and is available at http://www.eclipse.org/legal/epl-v10.html
 */

module ip-sgt-distribution-service-cfg {
    yang-version 1;
    namespace "urn:opendaylight:params:xml:ns:yang:controller:config:ip:sgt:distribution:service:cfg";
    prefix "ip-sgt-distribution-service-cfg";

    import config { prefix config; revision-date 2013-04-05; }
    import opendaylight-md-sal-binding { prefix mdsal; revision-date 2013-10-28; }
    import ietf-inet-types { prefix inet; revision-date 2013-07-15; }

    description
        "This module contains the base YANG definitions for
        ip/sgt distribution service implementation.";

    revision "2016-07-15" {
        description
            "Initial revision.";
    }

    identity ip-sgt-distribution-service {
        base "config:module-type";

        config:java-name-prefix IpSgtDistributionService;
    }

    // Augments the 'configuration' choice node under modules/module.
    augment "/config:modules/config:module/config:configuration" {
        case ip-sgt-distribution-service {
            when "/config:modules/config:module/config:type = 'ip-sgt-distribution-service'";
        }
    }
}
