/*
 * Copyright (c) 2016 Cisco Systems, Inc. and others.  All rights reserved.
 *
 * This program and the accompanying materials are made available under the
 * terms of the Eclipse Public License v1.0 which accompanies this distribution,
 * and is available at http://www.eclipse.org/legal/epl-v10.html
 */

module sxp-ise-adapter-cfg {
    yang-version 1;
    namespace "urn:opendaylight:params:xml:ns:yang:controller:config:groupbasedpolicy:sxp-integration:sxp-ise-adapter";
    prefix "gpb-sxp-ise-adapter-cfg";

    import config { prefix config; revision-date 2013-04-05; }
    import opendaylight-md-sal-binding { prefix mdsal; revision-date 2013-10-28; }
    import sxp-ep-provider-cfg { prefix gbp-sxp-ep; revision-date 2016-07-22; }

    description
        "This module contains the base YANG definitions for
          gbp-ise-adapter impl configuration.";

    revision "2016-06-30" {
        description
            "Initial revision.";
    }

    identity sxp-ise-adapter-impl {
        description
            "gbp-sxp-ise-adapter impl module";

        base "config:module-type";
        config:java-name-prefix Sxp-IseAdapterProvider;
    }

    // Augments the 'configuration' choice node under modules/module.
    augment "/config:modules/config:module/config:configuration" {
        case gbp-sxp-ise-adapter-impl {
            when "/config:modules/config:module/config:type = 'sxp-ise-adapter-impl'";
        }
    }
}
