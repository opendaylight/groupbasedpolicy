/*
 * Copyright (c) 2016 Cisco Systems, Inc. and others.  All rights reserved.
 *
 * This program and the accompanying materials are made available under the
 * terms of the Eclipse Public License v1.0 which accompanies this distribution,
 * and is available at http://www.eclipse.org/legal/epl-v10.html
 */

module gbp-sxp-ise-adapter-model {
    yang-version 1;
    namespace "urn:opendaylight:params:xml:ns:yang:controller:config:groupbasedpolicy:gbp-sxp-ise-adapter:model";
    prefix "gbp-sxp-ise-adapter-model";

    import gbp-common { prefix gbp-common; revision-date 2014-04-21; }
    import sxp-database { prefix sxp-database; revision-date 2016-03-08; }
    import ietf-inet-types { prefix inet; revision-date 2013-07-15; }
    import ietf-yang-types {prefix yang; revision-date "2013-07-15";}

    description
        "This module contains the YANG definitions for
          gbp-sxp-ise-adapter implementation.";

    revision "2016-06-30" {
        description
            "Initial revision.";
    }

    container gbp-sxp-ise-adapter {
        description "root point for ise connection info and sgt harvest status";

        container ise-source-config {
            description "connection + credentials for ise-rest-api connection and target tennant";
            config true;

            leaf tenant {
               type gbp-common:tenant-id;
               mandatory true;
               description
                    "tenant for all extracted sgt";
            }

            leaf sgt-range-min {
                description "minimal sgt used by this tenant";
                type sxp-database:sgt;
            }

            leaf sgt-range-max {
                description "maximal sgt used by this tenant";
                type sxp-database:sgt;
            }

            container connection-config {
                description "rest connection configuration part";

                leaf ise-rest-url {
                    description "base uri to ise-rest-api";
                    mandatory true;
                    type inet:uri;
                }

                leaf connection-timeout {
                    description "connection timeout in milliseconds";
                    type uint16;
                    default 5000;
                }

                leaf read-timeout {
                    description "read from rest timeout in milliseconds";
                    type uint16;
                    default 5000;
                }

                list header {
                    description "request headers in form key+value";
                    key name;

                    leaf name {
                        type string;
                    }
                    leaf value {
                        type string;
                    }
                }
            }
        }

        container ise-harvest-status {
            description "result of sgt harvest from ise-rest-api and generating endpoint policy templates";
            config false;

            leaf success {
                description "true if all operations succeeded";
                type boolean;
            }

            leaf reason {
                description "failure detail";
                type string;
            }

            leaf templates-written {
                description "amount of endpoint templates written";
                type uint16;
            }

            leaf timestamp {
                description "stamped upon sgts harvested and templates written";
                type yang:date-and-time;
            }
        }
    }
}
