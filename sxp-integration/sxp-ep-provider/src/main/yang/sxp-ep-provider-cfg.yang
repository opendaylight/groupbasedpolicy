/*
 * Copyright (c) 2016 Cisco Systems, Inc. and others.  All rights reserved.
 *
 * This program and the accompanying materials are made available under the
 * terms of the Eclipse Public License v1.0 which accompanies this distribution,
 * and is available at http://www.eclipse.org/legal/epl-v10.html
 */

module sxp-ep-provider-cfg {
    yang-version 1;
    namespace "urn:opendaylight:params:xml:ns:yang:controller:config:groupbasedpolicy:sxp-integration:sxp-ep-provider";
    prefix "sxp-ep-prvd-cfg";

    import config { prefix config; revision-date 2013-04-05; }
    import opendaylight-md-sal-binding { prefix mdsal; revision-date 2013-10-28; }
    import groupbasedpolicy-cfg {prefix gbpcfg; revision-date 2015-11-06; }
    import sxp-database { prefix sxp-database; revision-date 2016-03-08; }

    description
        "This module contains the base YANG definitions for
          sxf-integration : sxp-ep-provider impl configuration.";

    revision "2016-07-22" {
        description
            "Initial revision.";
    }

    identity sxp-ep-provider-impl {
        description
            "sxp-ep-provider impl module";

        base "config:module-type";
        config:provided-service sxp-ep-provider;
        config:java-name-prefix SxpEpProviderProvider;
    }

    identity sxp-ep-provider {
        description
            "sxp-ep-provider injection point service for template provider";

        base "config:service-type";
        config:java-class "org.opendaylight.groupbasedpolicy.sxp.ep.provider.spi.SxpEpProviderProvider";
    }

    // Augments the 'configuration' choice node under modules/module.
    augment "/config:modules/config:module/config:configuration" {
        case sxp-ep-provider-impl {
            when "/config:modules/config:module/config:type = 'sxp-ep-provider-impl'";
        }
    }

    container sgt-generator-config {
        description "sgt-generator configuration";
        leaf sgt-low {
            type sxp-database:sgt;
            mandatory true;
            description "minimal SGT value to be used by sgt-generator";
        }
        leaf sgt-high {
            type sxp-database:sgt;
            mandatory true;
            description "maximal SGT value to be used by sgt-generator";
        }
    }
}
